[DOCUMENT]
TITLE: Native controls

[GRAMMAR]
ELEMENTS:
- TAG: REQUIREMENT
  FIELDS:
  - TITLE: UID
    TYPE: String
    REQUIRED: True
  - TITLE: STATEMENT
    TYPE: String
    REQUIRED: True
  RELATIONS:
  - TYPE: Parent
  - TYPE: Child
  - TYPE: Parent
    ROLE: H
  - TYPE: Parent
    ROLE: R
  - TYPE: Child
    ROLE: Q

[REQUIREMENT]
UID: A
STATEMENT: A
RELATIONS:
- TYPE: Parent
  VALUE: B

[REQUIREMENT]
UID: B
STATEMENT: B
RELATIONS:
- TYPE: Parent
  VALUE: A

[REQUIREMENT]
UID: Z
STATEMENT: Z

[REQUIREMENT]
UID: ISOLATED
STATEMENT: ISOLATED
