[DOCUMENT]
TITLE: Native controls

[GRAMMAR]
ELEMENTS:
- TAG: REQUIREMENT
  FIELDS:
  - TITLE: UID
    TYPE: String
    REQUIRED: True
  - TITLE: STATEMENT
    TYPE: String
    REQUIRED: True
  RELATIONS:
  - TYPE: Parent
  - TYPE: Child
  - TYPE: Parent
    ROLE: H
  - TYPE: Parent
    ROLE: R
  - TYPE: Child
    ROLE: Q

[REQUIREMENT]
UID: A
STATEMENT: A
RELATIONS:
- TYPE: Child
  VALUE: B
  ROLE: Q

[REQUIREMENT]
UID: B
STATEMENT: B
RELATIONS:
- TYPE: Child
  VALUE: A
  ROLE: Q

[REQUIREMENT]
UID: Z
STATEMENT: Z

[REQUIREMENT]
UID: ISOLATED
STATEMENT: ISOLATED
