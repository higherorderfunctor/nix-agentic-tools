[DOCUMENT]
TITLE: Semble tree-sitter grammar injection

[GRAMMAR]
IMPORT_FROM_FILE: @repo

[DECISION]
UID: DEC-ARCH-COLOCATION
TITLE: Settled architecture lives in a .sdoc directory beside the code
AUTHORED_BY: llm
STATUS: open
RETIRES_ON: >>>
A source-comment extractor exists, at which point these nodes either move into
the source files they describe or stay put and the extractor feeds them.
<<<
STATEMENT: >>>
Architecture nodes that describe a specific package live in a .sdoc directory
next to that package, not under docs/plans. Each node names the source file it
describes with a File relation. Line anchors are recorded in prose until an
extractor can carry them.

The competing option, deferred: keep every node under docs/ and rely on general
source extractors to associate them with code. That option needs the extractor
to exist first, so it cannot be chosen today.
<<<
RATIONALE: >>>
Colocation works with no tooling. Plans decay and are collected; settled
architecture about a package should outlive the plan that produced it and should
move with the package if it moves.
<<<
NOTES: >>>
Human acceptance needed. Both options are live and the choice is reversible: the
nodes carry global UIDs, so relocating them changes no edge.
<<<

[MECHANISM]
UID: MECH-SEMBLE-EXTRA-GRAMMARS
TITLE: Semble loads extra tree-sitter grammars from the Nix store
DEPTH: implemented
AUTHORED_BY: llm
STATEMENT: >>>
The semble package is patched so that a grammar lookup failing against its
bundled set falls through to a generated loader that opens store-backed parser
libraries by ctypes and wraps them in a tree-sitter capsule. Grammar packages
are supplied through the ai.programs.semble.grammars option and must expose a
language attribute and a compiled parser output.
<<<
RATIONALE: >>>
This keeps the upstream bundle intact and avoids its mutable extraction cache.
<<<
PARENT_FP: DEC-ARCH-COLOCATION:0000000
RELATIONS:
- TYPE: Parent
  VALUE: DEC-ARCH-COLOCATION
  ROLE: Governed_By
- TYPE: File
  VALUE: packages/semble/lib/withGrammars.nix
- TYPE: File
  VALUE: packages/semble/patches/extra-grammars.patch

[MECHANISM]
UID: MECH-SEMBLE-PATH-MAPPINGS
TITLE: Path mappings assign non-standard filenames to a language and index
DEPTH: implemented
AUTHORED_BY: llm
STATEMENT: >>>
An ordered list of path patterns maps files to a language and to one of the
code, config or docs indexes. First match wins. A match overrides both
suffix-based language detection and content categorization, and participates in
file discovery, parser selection and cache validation.

Indexing sdoc files therefore requires a mapping, because discovery is
extension-driven and .sdoc is in no default extension set.
<<<
PARENT_FP: DEC-ARCH-COLOCATION:0000000
RELATIONS:
- TYPE: Parent
  VALUE: DEC-ARCH-COLOCATION
  ROLE: Governed_By
- TYPE: File
  VALUE: packages/semble/lib/withGrammars.nix

[DECISION]
UID: DEC-GRAMMAR-PATCH-NOT-FORK
TITLE: Patch the upstream tree-sitter grammar in an overlay rather than forking it
AUTHORED_BY: human
STATUS: accepted
RETIRES_ON: >>>
Upstream revives and the patch stops applying, or the patch set grows past what
is reviewable as a diff, or the fix lands upstream and the patch is deleted.
<<<
STATEMENT: >>>
The sdoc tree-sitter grammar is consumed as an upstream source archive with a
small patch series applied in the overlay. No fork repository is created.

The patch targets the grammar definition, not the generated parser, so the
build must regenerate. A patched grammar definition with a stale generated
parser is a silent no-op: the build succeeds and the behavior is unchanged.

The grammar's own test corpus lives in this repository as a check, not in the
grammar source. Upstream ships none.
<<<
RATIONALE: >>>
Patching the definition keeps the diff around thirty reviewable lines. Forking
would mean carrying a regenerated parser of roughly eighteen thousand lines in
version history, for a change that is three rules.

Upstream has been dormant for 336 days, so drift risk is low, and fuzz-free
patch application makes any drift a loud build failure rather than a quiet
misapplication.

If the fix is accepted upstream later, a fork created at that point is a contribution
vehicle rather than a dependency, and a merged fix deletes the patch instead of
leaving a stale fork to reconcile.
<<<
NOTES: >>>
Two build details found by reading the nixpkgs grammar builder. Its generate
step runs a bare generate command after changing into the path declared in the
grammar metadata; this grammar declares no path and keeps its definition in a
subdirectory, so the step fails without an override. And the metadata declares
a version and a file-type list that both disagree with the repository state.
<<<
