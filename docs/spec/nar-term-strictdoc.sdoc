[DOCUMENT]
TITLE: strictdoc

[GRAMMAR]
IMPORT_FROM_FILE: @repo

[NARRATIVE]
UID: NAR-TERM-STRICTDOC
TITLE: strictdoc
AUTHORED_BY: llm
WIDGET: prose
TAGS: term
STATEMENT: >>>
The upstream package the format comes from.

Ruled by [LINK: DEC-SCRIBE-NAMES-THE-WRITER].
<<<
PARENT_FP: DEC-SCRIBE-NAMES-THE-WRITER:0000000
RELATIONS:
- TYPE: Parent
  VALUE: DEC-SCRIBE-NAMES-THE-WRITER
  ROLE: Cites
