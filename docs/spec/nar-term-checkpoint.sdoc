[DOCUMENT]
TITLE: checkpoint

[GRAMMAR]
IMPORT_FROM_FILE: @repo

[NARRATIVE]
UID: NAR-TERM-CHECKPOINT
TITLE: checkpoint
AUTHORED_BY: llm
WIDGET: prose
TAGS: term
STATEMENT: >>>
A joint that fires on a workflow moment: a commit, a push, a check.

Ruled by [LINK: DEC-JOINT-NOT-SURFACE].
<<<
PARENT_FP: DEC-JOINT-NOT-SURFACE:0000000
RELATIONS:
- TYPE: Parent
  VALUE: DEC-JOINT-NOT-SURFACE
  ROLE: Cites
