[DOCUMENT]
TITLE: The ruled vocabulary

[GRAMMAR]
IMPORT_FROM_FILE: @repo

[NARRATIVE]
UID: NAR-CANON-WORDS
TITLE: The ruled vocabulary
AUTHORED_BY: llm
WIDGET: glossary
PLACE: tab
TAGS: terms, glossary
STATEMENT: >>>
The ruled words: every term narrative in the canon, each citing the decision that ruled it. Use them, and correct drift on sight.
<<<
PARENT_FP: NAR-TERM-CANON:0000000
RELATIONS:
- TYPE: Parent
  VALUE: NAR-TERM-CANON
  ROLE: Cites
- TYPE: Child
  VALUE: NAR-TERM-JOINT
  ROLE: Contains
- TYPE: Child
  VALUE: NAR-TERM-CHECKPOINT
  ROLE: Contains
- TYPE: Child
  VALUE: NAR-TERM-SCRIBE
  ROLE: Contains
- TYPE: Child
  VALUE: NAR-TERM-SDOC
  ROLE: Contains
- TYPE: Child
  VALUE: NAR-TERM-STRICTDOC
  ROLE: Contains
- TYPE: Child
  VALUE: NAR-TERM-CANON
  ROLE: Contains
- TYPE: Child
  VALUE: NAR-TERM-BEADS
  ROLE: Contains
