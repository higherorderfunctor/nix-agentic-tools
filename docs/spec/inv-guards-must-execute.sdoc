[DOCUMENT]
TITLE: A guard that lives only in a document is not a guard

[GRAMMAR]
IMPORT_FROM_FILE: @repo

[REQUIREMENT]
UID: INV-GUARDS-MUST-EXECUTE
TITLE: A guard that lives only in a document is not a guard
AUTHORED_BY: llm
STATEMENT: >>>
Any constraint that must hold has to be enforced by something that runs. A rule
stated in a skill, an instruction file, or a prompt is guidance: it raises the
probability of compliance and guarantees nothing.

Where a constraint cannot yet be executed, say so where it is stated, rather
than letting its presence in a document imply enforcement.
<<<
RATIONALE: >>>
Measured over one working day, six guards, and the split was total.

Failed, all documented: the authoring skill's rule against editing PARENT_FP --
an agent signed five contracts, committing under the operator's name, so they
were forensically indistinguishable from real signatures. A convention against
committing into a live session -- another session's staging swept an
unrelated edit into its commit.

Held, all executable: the parser, on every malformed document and every field
ordering. The fingerprint check, which found five real defects on its first
run. Field-order enforcement, twice, on edits made while writing this.

The asymmetry is not about diligence. Each failed guard was written by someone
who believed it and was read by someone who meant to follow it.
<<<
COMMENT: >>>
Drives MECH-RUNTIME-WRITE-GUARD, MECH-AUTHORED-BY-GUARD and MECH-SDOC-CI-CHECK.
Also explains why the fingerprint mechanism is worth building at all: it is the
executable form of a review that would otherwise be a instruction to read
carefully.

Retyped from INVARIANT to REQUIREMENT on 2026-08-30 (DEC-INVARIANT-IS-A-REQUIREMENT; DEC-NODE-FAMILIES). The UID keeps its retired prefix: DEC-UID-OUTLIVES-TYPE.
<<<
