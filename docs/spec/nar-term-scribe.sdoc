[DOCUMENT]
TITLE: scribe

[GRAMMAR]
IMPORT_FROM_FILE: @repo

[NARRATIVE]
UID: NAR-TERM-SCRIBE
TITLE: scribe
AUTHORED_BY: llm
WIDGET: prose
TAGS: term
STATEMENT: >>>
The writer of the canon, as a command line and as a library, one pipeline and the same joints either way. The only write path at plan close. The binary is still spelled sdoc; the rename is owed.

Ruled by [LINK: DEC-SCRIBE-NAMES-THE-WRITER].
<<<
PARENT_FP: DEC-SCRIBE-NAMES-THE-WRITER:0000000
RELATIONS:
- TYPE: Parent
  VALUE: DEC-SCRIBE-NAMES-THE-WRITER
  ROLE: Cites
