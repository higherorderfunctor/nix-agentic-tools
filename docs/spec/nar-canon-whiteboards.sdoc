[DOCUMENT]
TITLE: Documents

[GRAMMAR]
IMPORT_FROM_FILE: @repo

[NARRATIVE]
UID: NAR-CANON-WHITEBOARDS
TITLE: Documents
AUTHORED_BY: llm
WIDGET: index
PLACE: card
TAGS: roots
STATEMENT: >>>
Every document in the canon, one card each: a document is a tree of narratives whose root nothing contains, and it appears here by being written. A document is no longer a tab of its own ([LINK: DEC-TABS-ARE-A-DECLARED-VOCABULARY]) -- its own screens open from Start, under the system that holds it, and its tab narratives join the tabs they name.
<<<
PARENT_FP: NAR-TERM-CANON:0000000
RELATIONS:
- TYPE: Parent
  VALUE: NAR-TERM-CANON
  ROLE: Cites
- TYPE: Parent
  VALUE: DEC-TABS-ARE-A-DECLARED-VOCABULARY
  ROLE: Cites
