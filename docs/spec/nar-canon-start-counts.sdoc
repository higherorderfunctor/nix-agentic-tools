[DOCUMENT]
TITLE: What the canon holds

[GRAMMAR]
IMPORT_FROM_FILE: @repo

[NARRATIVE]
UID: NAR-CANON-START-COUNTS
TITLE: What the canon holds
AUTHORED_BY: llm
WIDGET: index
PLACE: section
TAGS: nodes
STATEMENT: >>>
Every node of the canon, counted by type and by where it lives, over the systems switched on.
<<<
PARENT_FP: NAR-TERM-CANON:0000000
RELATIONS:
- TYPE: Parent
  VALUE: NAR-TERM-CANON
  ROLE: Cites
