[DOCUMENT]
TITLE: beads

[GRAMMAR]
IMPORT_FROM_FILE: @repo

[NARRATIVE]
UID: NAR-TERM-BEADS
TITLE: beads
AUTHORED_BY: llm
WIDGET: prose
TAGS: term
STATEMENT: >>>
The agent's private working store, one per identity, in its own repository, not part of the canon. Canon and beads differ in authority, not shape.

Ruled by [LINK: DEC-CANON-NAMES-THE-COMMITTED-CONTENTS].
<<<
PARENT_FP: DEC-CANON-NAMES-THE-COMMITTED-CONTENTS:0000000
RELATIONS:
- TYPE: Parent
  VALUE: DEC-CANON-NAMES-THE-COMMITTED-CONTENTS
  ROLE: Cites
