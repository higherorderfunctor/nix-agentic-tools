[DOCUMENT]
TITLE: sdoc

[GRAMMAR]
IMPORT_FROM_FILE: @repo

[NARRATIVE]
UID: NAR-TERM-SDOC
TITLE: sdoc
AUTHORED_BY: llm
WIDGET: prose
TAGS: term
STATEMENT: >>>
The file format and its grammar, nothing else.

Ruled by [LINK: DEC-SCRIBE-NAMES-THE-WRITER].
<<<
PARENT_FP: DEC-SCRIBE-NAMES-THE-WRITER:0000000
RELATIONS:
- TYPE: Parent
  VALUE: DEC-SCRIBE-NAMES-THE-WRITER
  ROLE: Cites
