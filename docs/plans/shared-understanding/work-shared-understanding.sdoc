[DOCUMENT]
TITLE: Shift the system toward shared human-and-LLM reasoning

[GRAMMAR]
IMPORT_FROM_FILE: @repo

[WORK]
UID: WORK-SHARED-UNDERSTANDING
TITLE: Shift the system toward shared human-and-LLM reasoning
AUTHORED_BY: llm
STATEMENT: >>>
The grooming thread for the operator's 2026-09-01 direction. Their goal
sentence, verbatim because it reads two ways: "the goal crosses the whole
system but it's to shift the board as a whole for human reasoning (include
the color edges with it)." Reading one: the BOARD APP is the target and the
rest of the system is what the work crosses. Reading two: "board" is loose
shorthand and the shift is system-wide. This carve leans reading two --
grammars, plan machinery, presentation and the app as peer groups -- and the
operator separates intent from that reading at grooming. Their mission line
for the whole branch: promote a shared understanding between human and LLM;
their sketch of the axes, offered "on a whim, don't take literally": the
what (spec/presentation), the how/when (plan), the why (annotation), the
who (authorship).

Worked agile and HITL: no order enforced, the operator pivots to whatever
they judge the worst gap when a session works this thread. The children are
concept groups holding work items carved from the dump; each item's COMMENT
carries the operator's verbatim where meaning or scope is ambiguous.
Nothing here converts to spec or presentation nodes without a grooming
session -- REQ-BOARD-GRAMMAR-DRIVEN is the one requirement the operator
offered, hedged (see its COMMENT).

Old plans are NOT superseded by this thread's existence: reconciling them
(WORK-OLD-PLANS-RECONCILE) is an explicit grooming session. Related work
living elsewhere: WORK-BOARD-FILTER-MODEL stays in whiteboard-view.
<<<
