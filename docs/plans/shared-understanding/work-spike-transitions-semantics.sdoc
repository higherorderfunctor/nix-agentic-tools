[DOCUMENT]
TITLE: Spike: pytransitions/transitions as the semantics engine

[GRAMMAR]
IMPORT_FROM_FILE: @repo

[WORK]
UID: WORK-SPIKE-TRANSITIONS-SEMANTICS
TITLE: Spike: pytransitions/transitions as the semantics engine
DEPTH: implemented
AUTHORED_BY: llm
STATEMENT: >>>
A spike on the transitions Python library (https://github.com/pytransitions/transitions)
as the engine behind instance semantics -- the lifecycle ladders (DEPTH,
STATUS, STANDING) modeled as state machines with events and guards. The
library reads as simple enough that it could either influence a Nix
rendering of the same state machine, or a thin config wrapper built around
the library itself; which of the two is still open, and is the point of the
spike. The semantic rules the engine would run are meant to be stored as
literal scripts embedded directly in sdoc fields, which is what ties this to
WORK-SDOC-EMBEDDED-LANGUAGE-FIELDS (the field-plus-language-companion
mechanism) and to WORK-UC-WORK-ITEMS-AS-BASH (the sibling use case of a WORK
item whose content is a literal, executable script).
<<<
NOTES: >>>
Operator, 2026-09-02, verbatim: "spike using
https://github.com/pytransitions/transitions for semantics engine. looks
simple, possibly to influence a nix version or config wrapper.
- relate the node about scripts embedded in sdoc (literal scripts). store
  semantic rules in literal sdocs"

Landed 2026-09-03 (46cd3cf and the commit before it) as
dev/scripts/sdoc_semantics/: a `transitions`-backed engine (engine.py, the
only module that imports the library) with declarations in direct Python
under machines/ -- one file per field (depth.py, status.py,
authored_by.py), listed in registry.py in presentation order. This is an
explicit WAIVER of DEC-LAYER-STACK for the spike ("for the spike the
semantics can be written in direct python" -- operator, stated in
engine.py's own docstring); machines/ is a transcription surface meant to be
reshaped by hand, and becomes the fixture the typed Nix surface has to
reproduce once SLICE-BEHAVIOUR-MODEL lands, not the thing that ships.

WHERE TO SHAPE a lifecycle: edit the one file under
dev/scripts/sdoc_semantics/machines/ for that field; registry.py's _ORDERED
tuple is the single place that lists which machines exist and in what
order. `scribe semantics <TYPE>` and the board's Grammars tab both read the
same registry, so a change to a machine file shows up in both without
further wiring.

Three questions deliberately left open, transcribed as rules on the
declarations themselves rather than settled here: whether DEPTH may ever
fall (a design invalidated by a spike arguably returns to needs-design, but
a falling DEPTH erases the record it once stood higher -- nobody has
ruled); whether `implemented` and `verified` belong on the DEPTH ladder at
all, since they describe the artifact rather than the thinking; and whether
one machine per FIELD (what ships) or one machine per (type, field) is the
right grain -- the former is cheaper and is what six node types sharing one
DEPTH ladder assumes, the latter would let a REQUIREMENT and a WORK disagree
about what a rung means, at the cost of keeping six tables aligned.

Revisited 2026-09-03: the engine choice was re-opened before shaping
(WORK-REVISIT-SEMANTICS-ENGINE). The assessment
(EV-SEMANTICS-ENGINE-ALTERNATIVES) found no library that carries the whole
vocabulary, and DEC-SEMANTICS-MODEL-IS-DATA (open) proposes the model as a
data document over a standard-library interpreter, with transitions removed.
The three open questions above are unchanged by that and stay the operator's.
<<<
RELATIONS:
- TYPE: Parent
  VALUE: WORK-SEMANTICS-AND-WORDS
  ROLE: Assumes
- TYPE: Parent
  VALUE: WORK-SDOC-EMBEDDED-LANGUAGE-FIELDS
  ROLE: Assumes
- TYPE: Child
  VALUE: EV-TRANSITIONS-ENGINE-SPIKE
  ROLE: Produces
- TYPE: Parent
  VALUE: MECH-SEMANTICS-DEFINITION-BOUNDARY
  ROLE: Crosses
