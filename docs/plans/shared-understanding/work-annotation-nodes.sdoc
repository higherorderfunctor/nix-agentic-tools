[DOCUMENT]
TITLE: An annotation class: question, contradiction, comment, gap, known issue

[GRAMMAR]
IMPORT_FROM_FILE: @repo

[WORK]
UID: WORK-ANNOTATION-NODES
TITLE: An annotation class: question, contradiction, comment, gap, known issue
AUTHORED_BY: llm
STATEMENT: >>>
"Annotations" names a grammar FILE, not a single node type: the annotations
side of the three-way split in WORK-GRAMMAR-FILE-SPLIT (assuming multiple
grammars are allowed -- that item's spike is still unrun). The file holds
one or more node types that relate to one or more nodes in any grammar in
the graph to annotate them. Chainable for threads. Kinds named so far:
gaps, review comments, the operator's open questions about something,
conflicts between two nodes that the LLM finds, and possibly the
dirty-edges system. Last session's list -- question, contradiction,
comment, gap, known issue -- was the operator's first pass at the same set.
The class is open-ended, not this enumeration. This supersedes the earlier
sidecar-for-edge-fields design.

The existing COMMENTARY element would live in that file, but the operator
is not settled on keeping it as ONE type: its use cases carry different
semantics, and one type is hard to tell apart in the views. Their lean, not
a ruling: one node type per distinct semantics, because that is how the
board colours things today (the rule behind it is
WORK-SPLIT-TYPE-ON-SEMANTIC-FIELD); open to a field or something else
instead. The concrete want: a GAP must read loud and red in every view --
"do not pass go".

Special semantics are under consideration, none settled. "Not merged to
main" was said under uncertainty. Alternatives the operator has since
named: a plan cannot be ready to execute while certain annotations (gaps)
are attached to it; or a plan is blocked only at the point of the conflict
until it is resolved, not as a whole.

To reconcile at grooming: COMMENTARY (STANDING open/closed/withdrawn,
CLOSES_ON, EDGE; DEC-COMMENTARY-IS-THE-FIFTH-FAMILY is open, nothing is one
yet) moves into the annotations file and either survives as one of its
types or dissolves into them. Which of the two is undecided.
<<<
COMMENT: >>>
Verbatim on the open-ended class: "In the past I mentioned a class of nodes
that may not persist to main. Below covers a subset of what might be
possible based on semantic rules we come up with."

Ambiguity the operator flagged themselves -- USE_CASE's home: "coverage: use
case? I think it slots here as a form of contract but could also be seen as
work (test coverage)."

Verbatim on the lifecycle: "not 100% settled on not main. I'd rather have a
clean history, but some plans cannot be specced upfront, e.g., needs spike
or research. I'm still leaning not main, use a long-lived branch, completed
plans go to main. Work cannot start if conflicts though."

Overlap to resolve at grooming: the grammar ALREADY carries an empty
COMMENTARY element (STANDING open/closed/withdrawn, CLOSES_ON, EDGE;
DEC-COMMENTARY-IS-THE-FIFTH-FAMILY is open, nothing is one yet). The dump
does not mention it -- whether this annotation class extends, supersedes, or
coexists with COMMENTARY is unasked and unanswered.

Operator, 2026-09-01, verbatim: "annotations is meant to be one or more
nodes, in their own grammar, that can reference any node, in any grammar,
in the graph, assuming multiple grammars allowed (see 3). [...] the
annotations is meant to be like literally a node with relation to some
other node or nodes to annotate things like gaps, or review comments, or
my open questions about something, conflicts between two nodes (llm finds),
maybe even be the dirty edges system. the fields may have been about how to
handle different annotation types. diff node types if content different,
or same with just like a field on annotation type if same content. i
gave a list last session of a couple ideas. i was considering special
semantics around it. i originally said not merge to main, but that was
under 'i'm not sure about that'. it could be a plan cannot be ready to
execute with certain nodes like gaps. or at least the plan is blocked at
the point of conflict until resolved, not whole plan."

Changed 2026-09-01: the STATEMENT no longer records "work cannot start while
conflicts are open" as a stated rule, nor tags contradiction and gap as
"not main". The operator has downgraded both: "not merged to main" was
said under uncertainty, and the whole-plan block is now one alternative
beside a block at the point of conflict only. The annotation's shape is
now fixed as a node in its own grammar file with relations to its targets;
the earlier "a field suffices" wording is replaced by the explicit fork
between distinct node types and one type with a kind field.

Operator, 2026-09-01, verbatim: "annotations was meant to be the grammar
split. commentary is hard to eyeball in our views between the different
semantic meanings it may represent. i want to see GAP loud and red in our
views. my lean is node type since that's how things are colored today, but
i'd be open to field type or something. i was describing splitting the
grammar file up though (as well as discussing new node types) all in one
giant monologue of a prompt, so I get the confusion. annotations new
grammar file, commentary lives there, but i'm not settled on liking
commentary as different use cases have different semantics. actually i
think i also said that session that if a single field changes the
semantics of a node, we should consider the split simply to divide the
semantic rules. and it doubles as the visual cue I wanted cuz it's based on
the semantics (gap, red, bad, do not pass go)."

Changed 2026-09-01, second pass: the STATEMENT no longer says an annotation
is "a node, in its own grammar file" -- "annotations" is the grammar FILE,
holding one or more node types. The open fork "distinct node types vs one
type with a kind field" is restated with the operator's lean (one node type
per distinct semantics, open to a field) and its reason (the board colours
by type; a GAP must read red). The reconcile-with-COMMENTARY note now says
COMMENTARY moves into the annotations file and either survives as one of
its types or dissolves into them, replacing "extends, supersedes, or
coexists".

Operator, 2026-09-01, verbatim: "i don't want to dig into that, i was
trying to shape the plan you inherited so you can reason about it. you just
need to track the intent right now, it seems like low priority compared to
the other items to me. i don't even have settled models for the stuff it's
intended to annotate like the plan or spec stuff." Carver's reading: the
blocking-semantics question (which kinds block a plan, which only inform)
is PARKED; annotations rank below the plan-model and spec-model items,
because those are what an annotation attaches to, and they are not settled.

2026-09-02: operator now leans to annotations being WORK (see
WORK-ANNOTATIONS-ARE-WORK).
<<<
RELATIONS:
- TYPE: Parent
  VALUE: WORK-GRAMMAR-ARCHITECTURE
  ROLE: Assumes
- TYPE: Parent
  VALUE: MECH-BACKLOG-SHARED-UNDERSTANDING
  ROLE: Backlogged_In
