[DOCUMENT]
TITLE: Extend code linkage: strictdoc source traceability plus Nix and TypeScript extractors

[GRAMMAR]
IMPORT_FROM_FILE: @repo

[WORK]
UID: WORK-CODE-LINKAGE-EXTRACTORS
TITLE: Extend code linkage: strictdoc source traceability plus Nix and TypeScript extractors
AUTHORED_BY: llm
STATEMENT: >>>
Wire strictdoc's native source traceability so that a hard-coded render carries a File relation to the narrative it renders, and a change at either end dirties the edge and forces a review, ideally by an LLM. First case: the grammars grid in docs/sdoc/board/assets/grammars.js renders NAR-CANON-TYPES-GRID; today its glosses are copied prose in docs/sdoc/board/grammar-groups.json with no edge between them, so nothing notices when the narrative moves. Then extend the language coverage past what strictdoc ships (Python, the C family, Rust, Robot) with our own tree-sitter extractors: Nix modules and options, TypeScript types and interfaces. THE FEATURE IS NOW ON: REQUIREMENT_TO_SOURCE_TRACEABILITY is enabled in the repository's own strictdoc_config.py, and the operator's 2026-09-02 ruling keeps strictdoc's generic parser DISABLED -- only the configured glob manifest (dev/scripts/sdoc_extractors/registry.py) parses a file; every other path still gets indexed so a whole-file relation to it keeps resolving.

This is the buildout of MECH-NODE-CODE-LINKAGE-IS-PROSE, the observation that the link between a node and its code is prose in both directions and unchecked in both. That node lives in the strictdoc-tooling plan and is named here rather than related, because INV-NO-EXTERNAL-PLAN-REFS forbids a plan-to-plan Parent relation whatever its role. The assessment of what strictdoc gives, what the repo already has, the dirty-edge gap and the level of effort is EV-STRICTDOC-SOURCE-TRACEABILITY-LOE; its recommendation is to build the repo-side edge first and defer both the native feature and the readers.

Still open, the operator's call: option 1, render the grid from the narrative, versus option 2, keep the render in code and hang a dirty edge on it (see MECH-SDOC-BOARD-GRAMMARS-VIEW); where the code-side hash lives, strictdoc's HASH slot on the relation or PARENT_FP under a path key; and the direction of the edge, since the operator's phrasing has the render depend on the narrative while the canon's rules (nothing in the grid may depend on a narrative; MECHANISM has no Cites role) leave the narrative as the only lawful holder of that edge once NARRATIVE is given a File role.
<<<
COMMENT: >>>
Operator, 2026-09-02, verbatim, on option 1 (render from the narrative) versus option 2 (code plus a dirty edge): "on option 1, it isn't a no but before I invest more in that I feel like it would be whack-a-mole maintaining an inner DSL inside an sdoc for different views where simple relating code to spec is the generic abstraction using core ideas of canon like dirty refs. could be a forcing function to apply some real settled mechanics also like just general dirty edge ripples and what not."

Operator, 2026-09-02, verbatim, on the grid as code with a dirty edge: "so hard coding the grid becomes like @relation(REQ-1, scope=file) pointed to NAR-CANON-TYPES-GRID. If the narrative changes it dirties your edge to the hard coded grammar render in code forcing a review (ideally LLM). this is a core feature of canon we just haven't built out yet."

The opening paragraph of the operator's ask, running from "strict doc has native code integrations" through "not sure how easy it is to add other things like a nix module, typescript type/interface, etc.", was not available to the session that filed this node and is NOT reproduced here. Paste it verbatim from the session transcript; do not paraphrase it into this field.

Filed 2026-09-02 as the buildout item for MECH-NODE-CODE-LINKAGE-IS-PROSE. Not related to it by Crosses: that node lives in docs/plans/strictdoc-tooling/, and INV-NO-EXTERNAL-PLAN-REFS rules a plan-to-plan Parent relation, whatever its role, exactly the violation a spec-to-plan one is; the lane is named in the STATEMENT instead. Produces EV-STRICTDOC-SOURCE-TRACEABILITY-LOE, the assessment that preceded any build; the operator's read of it decides whether the repo-side edge, the native feature or the readers come first.

MVP landed 2026-09-02: 0496adf feat(strictdoc): add a tree-sitter language-item extractor with nix first, 6fbaa76 feat(strictdoc): let scribe write file relations with element and id, and show them in the board, 62a1be7 docs(strictdoc): add test file relations with element and id; nix extractor + get_reader patch; File relations carry ELEMENT/ID; feature flag NOT enabled (11 s under study); dirty edge deferred by the operator's scope ruling.

Operator, 2026-09-02, verbatim: "i assumed we were using the source linking feature. i prefer, or rather, require unless there is reason surfaced its a bad requirement, that the generic parser be disabled. i'd even be okay with disabling all internal parsers and only scanning for configured langs, langitems/queries. i'd prefer supporting sub-grammars (bash in nix) if technically possibly and reasonable. i'd recommend even considering glob matchers (extentionless bash, dont read every file and detect). Not sure how it works today. full manifest then filtered by extension, over just building the manifest from globs. glob not covered not in scope. i have no ambitions for generic matching at all."

Landed 2026-09-02: c64a0147 feat(strictdoc): turn source linking on with a glob manifest and no generic parser, 7d6886d1 feat(strictdoc): validate element and id on write and in a corpus check; show the item kind in the board. The design settles the ruling as: a glob decides what gets PARSED, never what gets INDEXED -- strictdoc's walk still visits every file, so a whole-file File relation to an unmatched path keeps resolving, and only the parse itself narrows to the configured manifest (dev/scripts/sdoc_extractors/registry.py); that is what lets the generic textX reader be disabled at no cost to existing whole-file relations. Measured on this corpus: export cold 9.3 s (was 15.4 s with the generic reader on), warm 2.8 s versus 2.1 s with the feature off -- the +0.6 s warm delta is strictdoc's own indexing of 1397 files and is accepted; scribe check held at 2.1 s, unchanged. The scribe daemon and the board server both run the code they had when they last started and need a restart (devenv up) before either runs what these two commits landed.
<<<
RELATIONS:
- TYPE: Parent
  VALUE: WORK-CANON-STRUCTURE
  ROLE: Assumes
- TYPE: Child
  VALUE: EV-STRICTDOC-SOURCE-TRACEABILITY-LOE
  ROLE: Produces
- TYPE: Child
  VALUE: EV-STRICTDOC-EXPORT-TIMING
  ROLE: Produces
