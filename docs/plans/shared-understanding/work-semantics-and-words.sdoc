[DOCUMENT]
TITLE: Naming and semantics get a home

[GRAMMAR]
IMPORT_FROM_FILE: @repo

[WORK]
UID: WORK-SEMANTICS-AND-WORDS
TITLE: Naming and semantics get a home
AUTHORED_BY: llm
STATEMENT: >>>
Concept group: naming and semantics. Holds glossary-per-node, semantic
conflict tracking.
<<<
RELATIONS:
- TYPE: Parent
  VALUE: WORK-SHARED-UNDERSTANDING
  ROLE: Assumes
- TYPE: Parent
  VALUE: MECH-BACKLOG-SHARED-UNDERSTANDING
  ROLE: Backlogged_In
