[DOCUMENT]
TITLE: Whether an Assumes edge is weaker than the other roles

[GRAMMAR]
IMPORT_FROM_FILE: @repo

[DECISION]
UID: DEC-ASSUMES-CONTRACT-BEARING
TITLE: Whether an Assumes edge is weaker than the other roles
AUTHORED_BY: llm
STATUS: open
RETIRES_ON: >>>
The first Assumes edge somebody wants to sign, or milestone five's ripple model landing — whichever comes first.
<<<
STATEMENT: >>>
Measured over the 144-node graph, 0 of 14 Assumes edges carry a PARENT_FP entry, while Governed_By carries one on 28 of 39 and Crosses on 3 of 29. The skill's fingerprint ladder runs strictly downward — DECISION to MECHANISM to SLICE — and has no place for the same-tier MECHANISM-to-MECHANISM (7 edges) and SLICE-to-SLICE (6 edges) that make up thirteen of the fourteen. Decide whether Assumes is contract-bearing.
<<<
RATIONALE: >>>
Either Assumes is deliberately not contract-bearing, in which case fp-accept should refuse to sign one and say so, or it is and fourteen edges are unsigned. Today neither is written down, and a uniform absence is indistinguishable from nobody having got round to it.
<<<
COMMENT: >>>
The fingerprint face is named in committed text: `MECH-RELATION-TARGET-TYPE-LINT`'s COMMENT cites this UID directly, twice.

Absorbs the proposed `DEC-CLOSURE-EDGE-ROLES`.
<<<
