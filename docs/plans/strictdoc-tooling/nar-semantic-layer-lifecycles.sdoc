[DOCUMENT]
TITLE: How a node changes state

[GRAMMAR]
IMPORT_FROM_FILE: @repo

[NARRATIVE]
UID: NAR-SEMANTIC-LAYER-LIFECYCLES
TITLE: How a node changes state
AUTHORED_BY: llm
WIDGET: rows
PLACE: screen
STATEMENT: >>>
Accepting and superseding decisions, deletion and the migration.

- A decision goes from open to accepted by a human, in conversation, with no gate. The semantic model has to be able to express a transition that nothing checks.
[LINK: NAR-SEMANTIC-LAYER-TYPE-DECISION] [LINK: NAR-SEMANTIC-LAYER-GAP-IDENTITY-HAS-NO-CARRIER]
> DECISION open -> accepted: identity:human, in conversation, no gate; the model must express a gateless move [WORKS]
- Today that acceptance is written under the agent's key. Either the human writes the STATUS through scribe under their own key, or a semantic-layer rule has to allow an agent to write it on a human's behalf.
[LINK: NAR-SEMANTIC-LAYER-TYPE-DECISION] [LINK: NAR-SEMANTIC-LAYER-GAP-IDENTITY-HAS-NO-CARRIER]
> split: that write lands under the identity:llm key today; either identity:human writes STATUS via scribe under its own key, or an L3 class rule allows it [GAP]
- A decision has never been rejected. Who may reject one is unwritten.
[LINK: NAR-SEMANTIC-LAYER-TYPE-DECISION]
> DECISION open -> rejected: never observed; who may do it is unwritten [GAP]
- When a decision's retirement condition fires it becomes superseded — done twice so far, by hand. There is no mark for 'expired', no transition, and no rule about who may do it.
[LINK: NAR-SEMANTIC-LAYER-TYPE-DECISION]
> DECISION -> superseded when RETIRES_ON fires (2x, by hand): no mark, no move, no class; "expired" must be materialized [GAP]
- An accepted decision's statement is frozen. Enforcing that needs the old value at the moment before scribe writes — a hook-layer capability that is not built.
[LINK: NAR-SEMANTIC-LAYER-TYPE-DECISION]
> accepted STATEMENT frozen: needs the old value at scribe.change pre; that L2 (hook-machinery) enabler is unbuilt [GAP]
- No gate reads a probe's STATUS. Under the pipeline reading the field dissolves: 'run' simply means an evidence node exists.
[LINK: MECH-SPIKE-IS-A-PIPELINE-TO-A-DECISION] [LINK: SPIKE-CONVERSION-SIGNAL] [LINK: NAR-SEMANTIC-LAYER-TYPE-EVIDENCE] [LINK: NAR-SEMANTIC-LAYER-TYPE-WORK]
> SPIKE STATUS: no gate consults it [FALLS OUT: MECH-SPIKE-IS-A-PIPELINE-TO-A-DECISION, run = an EVIDENCE node exists]
- Raising AUTHORED_BY from llm to human-adopted is a human act with no place to happen: no verb, no joint.
[LINK: NAR-SEMANTIC-LAYER-GAP-IDENTITY-HAS-NO-CARRIER]
> AUTHORED_BY raise (llm -> human-adopted): identity:human act with no place to happen [GAP]
- 'Supersede, never delete' is the rule for now. Expressed in the model it is 'no class may delete' — a handler refusing before scribe deletes.
[LINK: DEC-NO-DELETES-YET] [LINK: NAR-SEMANTIC-LAYER-TYPE-DECISION] [LINK: NAR-SEMANTIC-LAYER-GAP-IDENTITY-HAS-NO-CARRIER]
> delete: supersede, never delete = "no class may delete", a pre handler on scribe.change(delete) [OPEN: DEC-NO-DELETES-YET]
- Moving the canon onto the ruled types — three out, six in — is uncosted, has no work node, and waits on the plan-lifecycle decision. It must be done in one move, never half.
[LINK: DEC-PLAN-LIFECYCLE-OPEN] [LINK: NAR-SEMANTIC-LAYER-TYPE-REQUIREMENT] [LINK: NAR-SEMANTIC-LAYER-TYPE-USE-CASE] [LINK: NAR-SEMANTIC-LAYER-TYPE-EVIDENCE] [LINK: NAR-SEMANTIC-LAYER-TYPE-WORK] [LINK: NAR-SEMANTIC-LAYER-TYPE-NARRATIVE] [LINK: NAR-SEMANTIC-LAYER-GAP-GRAMMAR-CANNOT-SPELL-THE-VOCABULARY] [LINK: NAR-SEMANTIC-LAYER-GAP-MEMBERSHIP-AND-COLLECTION-CONTRADICT]
> grid migration: SLICE|INVARIANT|SPIKE out, REQUIREMENT|USE CASE|EVIDENCE|WORK|NARRATIVE|PLAN in; uncosted, no WORK node, gated on DEC-PLAN-LIFECYCLE-OPEN, never half-applied [GAP]
- Four questions left over from the abandoned two-grammar sketch: a tier field versus nesting depth; whether 'ungroomed' is a tier or a type; whether RATIONALE stays optional on a decision; and a plan with no edge to its members.
[LINK: NAR-SEMANTIC-LAYER-TYPE-DECISION]
> held from the two-grammar sketch: TIER vs containment depth; ungroomed as tier or type; RATIONALE optional on DECISION; PLAN without an edge [UNADDRESSED]
<<<
PARENT_FP: >>>
DEC-LAYER-STACK:0000000
DEC-NO-DELETES-YET:0000000
DEC-PLAN-LIFECYCLE-OPEN:0000000
MECH-SPIKE-IS-A-PIPELINE-TO-A-DECISION:0000000
NAR-SEMANTIC-LAYER-GAP-GRAMMAR-CANNOT-SPELL-THE-VOCABULARY:0000000
NAR-SEMANTIC-LAYER-GAP-IDENTITY-HAS-NO-CARRIER:0000000
NAR-SEMANTIC-LAYER-GAP-MEMBERSHIP-AND-COLLECTION-CONTRADICT:0000000
NAR-SEMANTIC-LAYER-GAP-SEMANTICS-LIVE-IN-TOOLS-WITH-NO-OWNER:0000000
NAR-SEMANTIC-LAYER-TYPE-DECISION:0000000
NAR-SEMANTIC-LAYER-TYPE-EVIDENCE:0000000
NAR-SEMANTIC-LAYER-TYPE-MECHANISM:0000000
NAR-SEMANTIC-LAYER-TYPE-NARRATIVE:0000000
NAR-SEMANTIC-LAYER-TYPE-REQUIREMENT:0000000
NAR-SEMANTIC-LAYER-TYPE-USE-CASE:0000000
NAR-SEMANTIC-LAYER-TYPE-WORK:0000000
NAR-TERM-CANON:0000000
NAR-TERM-JOINT:0000000
NAR-TERM-SCRIBE:0000000
MECH-SEMBLE-EXTRA-GRAMMARS:0000000
<<<
RELATIONS:
- TYPE: Parent
  VALUE: NAR-SEMANTIC-LAYER-TYPE-MECHANISM
  ROLE: Cites
- TYPE: Parent
  VALUE: NAR-SEMANTIC-LAYER-TYPE-REQUIREMENT
  ROLE: Cites
- TYPE: Parent
  VALUE: NAR-SEMANTIC-LAYER-TYPE-WORK
  ROLE: Cites
- TYPE: Parent
  VALUE: NAR-SEMANTIC-LAYER-TYPE-EVIDENCE
  ROLE: Cites
- TYPE: Parent
  VALUE: NAR-SEMANTIC-LAYER-GAP-IDENTITY-HAS-NO-CARRIER
  ROLE: Cites
- TYPE: Parent
  VALUE: NAR-SEMANTIC-LAYER-TYPE-DECISION
  ROLE: Cites
- TYPE: Parent
  VALUE: MECH-SPIKE-IS-A-PIPELINE-TO-A-DECISION
  ROLE: Cites
- TYPE: Parent
  VALUE: DEC-LAYER-STACK
  ROLE: Cites
- TYPE: Parent
  VALUE: NAR-SEMANTIC-LAYER-GAP-SEMANTICS-LIVE-IN-TOOLS-WITH-NO-OWNER
  ROLE: Cites
- TYPE: Parent
  VALUE: DEC-NO-DELETES-YET
  ROLE: Cites
- TYPE: Parent
  VALUE: DEC-PLAN-LIFECYCLE-OPEN
  ROLE: Cites
- TYPE: Parent
  VALUE: NAR-SEMANTIC-LAYER-TYPE-USE-CASE
  ROLE: Cites
- TYPE: Parent
  VALUE: NAR-SEMANTIC-LAYER-TYPE-NARRATIVE
  ROLE: Cites
- TYPE: Parent
  VALUE: NAR-SEMANTIC-LAYER-GAP-GRAMMAR-CANNOT-SPELL-THE-VOCABULARY
  ROLE: Cites
- TYPE: Parent
  VALUE: NAR-SEMANTIC-LAYER-GAP-MEMBERSHIP-AND-COLLECTION-CONTRADICT
  ROLE: Cites
- TYPE: Parent
  VALUE: NAR-TERM-JOINT
  ROLE: Cites
- TYPE: Parent
  VALUE: NAR-TERM-SCRIBE
  ROLE: Cites
- TYPE: Parent
  VALUE: NAR-TERM-CANON
  ROLE: Cites
- TYPE: Parent
  VALUE: MECH-SEMBLE-EXTRA-GRAMMARS
  ROLE: Cites
