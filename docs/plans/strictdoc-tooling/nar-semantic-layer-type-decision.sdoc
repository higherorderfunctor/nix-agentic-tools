[DOCUMENT]
TITLE: decision

[GRAMMAR]
IMPORT_FROM_FILE: @repo

[NARRATIVE]
UID: NAR-SEMANTIC-LAYER-TYPE-DECISION
TITLE: decision
DEPTH: sketch
AUTHORED_BY: llm
WIDGET: prose
TAGS: DECISION
STATEMENT: >>>
A choice, open or closed. A decision changes what the norms are; an open decision is a question.

Also: normative and particular in the grid. [LINK: DEC-NODE-FAMILIES] moved it inside: once accepted it is a choice the specification must follow, so it can be violated like a requirement, and while open it is not yet in force. An accepted decision's statement is frozen; it is superseded, never edited.

State: STATUS -- open, accepted, rejected, superseded -- and RETIRES_ON, the condition under which it expires. No DEPTH and no fingerprint of its own.
<<<
PARENT_FP: DEC-NODE-FAMILIES:0000000
RELATIONS:
- TYPE: Parent
  VALUE: DEC-NODE-FAMILIES
  ROLE: Cites
