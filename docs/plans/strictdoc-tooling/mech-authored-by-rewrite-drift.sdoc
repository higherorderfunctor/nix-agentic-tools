[DOCUMENT]
TITLE: An agent rewriting a human-authored statement leaves the key on words the operator did not write

[GRAMMAR]
IMPORT_FROM_FILE: @repo

[EVIDENCE]
UID: MECH-AUTHORED-BY-REWRITE-DRIFT
TITLE: An agent rewriting a human-authored statement leaves the key on words the operator did not write
AUTHORED_BY: llm
STATEMENT: >>>
`MECH-AUTHORED-BY-GUARD` watches the human value appearing on a node. Nothing watches the statement underneath an existing human value changing. Measured over the branch's 69 sdoc-touching commits by parsing every node at every revision: 36 nodes had their STATEMENT changed after creation, and 10 of those carried `AUTHORED_BY: human` on both sides of the edit — `DEC-PLAN-LIFECYCLE-OPEN`, `MECH-PLAN-BEADS-SNAPSHOT`, `MECH-TREEFMT-SDOC`, `MECH-RUNTIME-WRITE-GUARD`, `INV-NO-EXTERNAL-PLAN-REFS`, `MECH-AUTHORED-BY-GUARD`, `MECH-FP-MAIN-LINEAGE`, `MECH-FP-GIT-FLOW-HAZARDS`, `MECH-AGENT-IDENTITY-KEYS`, `MECH-TESTS-AS-CONTRACT`. Six of the ten were rewritten in one commit, 91ae9322. That is 10 of the 31 human-authored nodes in a 144-node graph. Three shapes exist and the choice is the operator's: hash the statement into the key so a rewrite reads as stale, drop the key to llm on any rewrite by an agent, or forbid the rewrite and require the operator to restate.
<<<
RATIONALE: >>>
Which shape applies depends on whether the key claims the words or the origin of the node, and that is a semantics question rather than a plumbing one. The count is not a backlog of past mistakes: grooming sessions rewrite human-authored statements routinely and the corpus says so in its own voice — `MECH-TESTS-AS-CONTRACT`'s COMMENT records that its key still reads human while "everything after them was written by a model", flagged rather than corrected because only the operator turns that key.
<<<
COMMENT: >>>
Measured 2026-08-27 by replaying `git log --reverse -- '*.sdoc'` and diffing each node's STATEMENT between consecutive revisions; the same walk detects the 26 llm-node rewrites, so a zero for human nodes would have been a real absence. The guard `MECH-AUTHORED-BY-GUARD` builds sees this case and passes it: it classifies by what the baseline said about the key, and the key did not move.

Retyped from MECHANISM to EVIDENCE on 2026-08-30 by the mechanism mood test under DEC-NODE-FAMILIES, with high confidence after a second opinion: it records what was observed once, not how something always behaves. Noted for a later split: The opening sentence ('MECH-AUTHORED-BY-GUARD watches the human value appearing on a node. Nothing watches the statement underneath an existing human value changing') describes the guard's behaviour universally and is a small MECHANISM fragment; it frames the measurement rather than displacing it. The heuristic's 'guard' hits are all UID names and its 'forbid' is one of the three options. The UID keeps its prefix: DEC-UID-OUTLIVES-TYPE.
<<<
RELATIONS:
- TYPE: Parent
  VALUE: MECH-BACKLOG-STRICTDOC-TOOLING
  ROLE: Backlogged_In
