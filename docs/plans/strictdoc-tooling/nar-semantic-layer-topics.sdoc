[DOCUMENT]
TITLE: Topics

[GRAMMAR]
IMPORT_FROM_FILE: @repo

[NARRATIVE]
UID: NAR-SEMANTIC-LAYER-TOPICS
TITLE: Topics
AUTHORED_BY: llm
WIDGET: prose
PLACE: tab
TAGS: topics
STATEMENT: >>>
The sheet's thirteen topics in the sheet's order, one section each. A row is one line of the sheet: the headline, the nodes the line cited, the kinds of node it speaks about, the top gaps it feeds, and the verdict the sheet gave it. The sheet's closing section, the five top gaps, has a tab of its own.
<<<
RELATIONS:
- TYPE: Child
  VALUE: NAR-SEMANTIC-LAYER-NODE-STRUCT
  ROLE: Contains
- TYPE: Child
  VALUE: NAR-SEMANTIC-LAYER-ALLOWED-EDGES
  ROLE: Contains
- TYPE: Child
  VALUE: NAR-SEMANTIC-LAYER-PARENT-CHILD
  ROLE: Contains
- TYPE: Child
  VALUE: NAR-SEMANTIC-LAYER-FILES-AND-RETENTION
  ROLE: Contains
- TYPE: Child
  VALUE: NAR-SEMANTIC-LAYER-LIFECYCLES
  ROLE: Contains
- TYPE: Child
  VALUE: NAR-SEMANTIC-LAYER-IDENTITY
  ROLE: Contains
- TYPE: Child
  VALUE: NAR-SEMANTIC-LAYER-DIRTY-RIPPLE
  ROLE: Contains
- TYPE: Child
  VALUE: NAR-SEMANTIC-LAYER-GATES-BEYOND-THE-FSM
  ROLE: Contains
- TYPE: Child
  VALUE: NAR-SEMANTIC-LAYER-ON-DISK-MOVES
  ROLE: Contains
- TYPE: Child
  VALUE: NAR-SEMANTIC-LAYER-PLANS-IN-REFS
  ROLE: Contains
- TYPE: Child
  VALUE: NAR-SEMANTIC-LAYER-MULTI-STEP-WORK
  ROLE: Contains
- TYPE: Child
  VALUE: NAR-SEMANTIC-LAYER-FLOWS
  ROLE: Contains
- TYPE: Child
  VALUE: NAR-SEMANTIC-LAYER-UNPLACED
  ROLE: Contains
- TYPE: Child
  VALUE: NAR-SEMANTIC-LAYER-TOPICS-SOLID
  ROLE: Contains
