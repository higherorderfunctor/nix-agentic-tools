[DOCUMENT]
TITLE: Index sdoc documents in semble

[GRAMMAR]
IMPORT_FROM_FILE: @repo

[WORK]
UID: SLICE-SDOC-IN-SEMBLE
TITLE: Index sdoc documents in semble
DEPTH: verified
AUTHORED_BY: llm
STATEMENT: >>>
Package a tree-sitter grammar for the sdoc format as a flake output, add it to
ai.programs.semble.grammars, and register a path mapping assigning *.sdoc to
that language in the docs index. Add a load check modelled on the existing
extra-grammars check, parsing a real sdoc sample.
<<<
RATIONALE: >>>
The repository's flake instructions already require that a custom grammar absent
from nixpkgs be exposed as a flake package so the authenticated matrix publishes
it. Every mechanism this slice crosses is already implemented.
<<<
NOTES: >>>
Implemented: overlays/generic/tree-sitter-strictdoc.nix (flake package
tree-sitter-strictdoc, flattened via pkgs.ai.generic), wired into
ai.codex.programs.semble.grammars and mcp.pathMappings in devenv.nix (patterns
*.sdoc and *.sgra, content docs). Load check:
checks/module-eval.nix:module-semble-strictdoc-grammar-load. Regression/corpus
suite: checks/strictdoc-grammar-corpus.nix (see SPIKE-SGRA-PARSE for measured
counts). update-targets and cache-hit-parity rows added; both checks pass.

Chunking verified independently, not assumed: on a 8762-byte document the AST
chunker returns 17 chunks against line chunking's 12, and the boundaries land
on node headers and on field starts, so a node larger than the 750-character
target splits into its own fields. chunk() returning a list rather than None is
the proof the parser loaded; a fallback would have been a log warning only.

Retyped from SLICE to WORK on 2026-08-30 under DEC-SLICE-DECOMPOSES-TO-WORK and DEC-NODE-FAMILIES. The UID keeps its retired prefix: DEC-UID-OUTLIVES-TYPE.
<<<
RELATIONS:
- TYPE: Parent
  VALUE: MECH-SEMBLE-EXTRA-GRAMMARS
  ROLE: Crosses
- TYPE: Parent
  VALUE: MECH-SEMBLE-PATH-MAPPINGS
  ROLE: Crosses
- TYPE: Parent
  VALUE: SPIKE-SGRA-PARSE
  ROLE: Proven_By
