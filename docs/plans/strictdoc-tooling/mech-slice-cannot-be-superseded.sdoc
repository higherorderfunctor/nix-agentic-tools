[DOCUMENT]
TITLE: A slice has no way to say it was replaced

[GRAMMAR]
IMPORT_FROM_FILE: @repo

[MECHANISM]
UID: MECH-SLICE-CANNOT-BE-SUPERSEDED
TITLE: A slice has no way to say it was replaced
AUTHORED_BY: llm
STATEMENT: >>>
Superseded_By and Supersedes are declared on DECISION only, so a MECHANISM,
SLICE, INVARIANT or SPIKE whose subject is replaced has no way to say so.

The question this node asked -- whether the relation is extended, whether slices
are collected differently, or whether rewriting in place is the intended answer
-- is answered by DEC-SUPERSESSION-RULE, and the answer is "it depends on what
actually changed". Rewriting in place is correct when the deliverable survived
in a different shape. It is the wrong tool only for genuine
abandoned-and-replaced work, and the relation stays unextended until that
happens twice.

This node's remaining job is to be the LEDGER for that trigger: every genuine
case-3 instance on a non-DECISION node is recorded here, and the second one is
what promotes extending the relation from a proposal to work.

INSTANCES SO FAR: zero. The case that prompted this node was not one.
<<<
RATIONALE: >>>
The graph records what is true now and, through fingerprints, when a contract
changed. It has no way to record that a unit of work was replaced wholesale,
which is a different event from either.

Kept as a ledger rather than closed because a count is the only thing that
distinguishes a real gap from a felt one, and this node was filed on a case that
turned out not to be an instance.
<<<
COMMENT: >>>
RECLASSIFIED 2026-08-27. This node was filed after SLICE-STRICTDOC-OVERLAY's
statement was rewritten in place, on the reading that the rewrite lost a
transition. It did not. The deliverable -- an overlay keeping strictdoc current
-- still exists and still ships; only the implementation shape changed, from a
first-party build to a re-export of upstream's flake. The unit of work
delivered. So the rewrite was correct and the transition it "lost" was of shape,
not of work, and shape history belongs in COMMENT and the commit, where it went.

That leaves the count at zero, which is the point: the gap is real but
UNEXERCISED, and building the relation now would be speculative.

Cost of extending, measured 2026-08-27 and lower than when this was filed:
docs/sdoc/grammar.sgra is generated from packages/strictdoc-grammar/values.nix
since milestone one, so adding a relation role is a typed edit plus a
regeneration rather than a hand-edited grammar file.
<<<
