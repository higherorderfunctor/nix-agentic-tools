[DOCUMENT]
TITLE: Making the rules executable

[GRAMMAR]
IMPORT_FROM_FILE: @repo

[DECISION]
UID: DEC-EXECUTABLE-RULES-ROADMAP
TITLE: The rules become executable in five milestones, plumbing before migration
AUTHORED_BY: llm
STATUS: accepted
RETIRES_ON: >>>
The fifth milestone is verified, or a milestone's review changes the order or
the number of milestones.
<<<
STATEMENT: >>>
The rules of the design system become executable in five milestones, in this
order:

1. The grammar, generated from a typed Nix option surface, with a validation
   gate at commit time and in CI.
2. A command-line tool that is the only writer of sdoc files, with direct
   edits denied.
3. The behaviour model -- states, moves, gates, triggers, flows -- defined in
   Nix and rendered so it can be looked at.
4. That behaviour wired into the tool and into checkpoints at command, commit
   and merge time, with strictdoc's own hooks as the backstop.
5. This system's own semantics -- fingerprints, signing, the ripple, DEPTH --
   migrated onto that plumbing.

Every milestone is consumer-facing, so its option surface or verb list is
reviewed by the operator before the milestone is implemented. Milestones one
and two are separate slices; each milestone normally runs in its own session,
and the operator may continue from one to the next in the same session when
the first goes well. Migration waits for the plumbing. Whether a finished
milestone is worth integrating sooner is the operator's call.

The planning session that produced these nodes stays open, to re-slot a
milestone whose timing was wrong.
<<<
RATIONALE: >>>
In the operator's words, the activity began because a model produces sdoc in
incorrect formats, nothing validates a write when it happens, and the node
lifecycle could not be reasoned about from prose. Milestones one and two end
the first two problems without waiting on any lifecycle decision; milestone
three is where the lifecycle becomes something that can be looked at; only
after four does a rule run rather than get read, which is what
INV-GUARDS-MUST-EXECUTE asks for. Ordering migration last keeps the instance's
open decisions -- who signs, whether DEPTH may regress, agent identity -- from
blocking the plumbing.
<<<
NOTES: >>>
Accepted by the operator on 2026-08-25 with one expectation stated: design
happens inside each step and may reshape that step. The plan was deliberately
not designed in full up front, to move faster through this part; a step's
slice is a starting shape, not a finished contract, until its own review.

The evidence behind every milestone is the SPIKE-EXECUTABLE-RULES assessment
and the fold-in review of two outside research documents that followed it,
both held in the operator's working area outside the repository.

A step zero precedes milestone one: SLICE-STRICTDOC-OVERLAY, the overlay that
keeps strictdoc on the latest release. Not a milestone -- it has no consumer
surface to review -- but every milestone runs on it.
<<<

[SLICE]
UID: SLICE-STRICTDOC-OVERLAY
TITLE: Step zero -- an overlay that keeps strictdoc on the latest release
DEPTH: implemented
AUTHORED_BY: llm
STATEMENT: >>>
Add a first-party overlay for strictdoc that tracks upstream's latest GitHub
release, so every session, check and devShell in this repository runs the
current version and the nixpkgs version stops being a topic. Shape: a thin
override of the nixpkgs derivation carrying our version and source from a
sidecar, with the two dependency adjustments the current release needs -- a
newer reqif and a relaxed pygments pin -- registered like the other tracked
packages: an update-targets row on the release-tracking contract, a
cache-hit-parity row, and the strictdoc-using flake checks and the devShell
switched to the overlay package. No patches; if one is ever needed it applies
with fuzz disabled.

No operator review before implementation: this is plumbing, not a consumer
surface. Reviewed after: `strictdoc version` in the devShell and in the checks
reports the latest release, and the update sweep bumps it on its own.

Tracking main instead of releases is the operator's call per package, made on
release cadence and how stable main is; strictdoc ships roughly three releases
a month, so release tracking is the default here.
<<<
RATIONALE: >>>
Standing rule from the operator: any package used seriously gets an overlay
that tracks the latest release or main -- update cadence is never a
consideration, and the version in nixpkgs is never an input. Several sessions
noted the version gap and none built the overlay; this node exists so the next
session builds it rather than noting it again. Everything after it -- the
grammar gate, the CLI, the behaviour model -- is measured against the latest
release and should run on it.
<<<
PARENT_FP: DEC-EXECUTABLE-RULES-ROADMAP:0000000
NOTES: >>>
Precedents to follow: the thin Python override in overlays/git-tools/
git-revise.nix, the release-tracking update-targets row for beads, the
cache-hit-parity registry, and overlays/generic/tree-sitter-strictdoc.nix for
the fuzz-free patch flags should a patch ever appear. Group: dev-tools, the
same class as beads.

Implemented 2026-08-25: overlays/dev-tools/strictdoc.nix plus its
strictdoc-sources.json sidecar, registered in overlays/default.nix
(pkgs.ai.devTools.strictdoc, flattened to the .#strictdoc flake package), with
an update-targets row and a cache-hit-parity row. The two strictdoc-using
checks (strictdoc-fp-check, strictdoc-cycle-check) and the devShell now take
pkgs.ai.devTools.strictdoc instead of the nixpkgs attribute. No patches, so
the fuzz-free flags did not come up.

Measured: the pin moves 0.27.1 (nixpkgs) to 0.28.3 (upstream latest), and the
built binary reports 0.28.3. Upstream tags releases BARE -- 0.28.3, not
v0.28.3 -- so both the archive URL and the version check pass tagPrefix = "";
that is the one place this row differs from beads. Two dependency adjustments
were needed and no more: reqif, which nixpkgs carries at 0.0.54 against the
release's `reqif >= 0.1.0, == 0.1.*`, pinned inline at 0.1.0 because
mkUpdateScript rebuilds the sidecar from scratch and would erase a second
package's pin; and pygments, added to pythonRelaxDeps rather than overridden,
because the release pins it exactly at 2.21.0 against the pin's 2.20.0 and
overriding it would fork the closure of the whole Python set for one
patch-level move. The version claim is asserted in the derivation's
installCheckPhase rather than left to a session to notice, and that assertion
was positive-controlled: pointed at a version the binary does not report, the
build fails in installCheckPhase.

The whole design corpus formats and exports clean under 0.28.3, so the bump is
not a migration: nothing in the grammar or the existing nodes needed changing
to move off the nixpkgs version.

RETIRED 2026-08-27, two days later: the first-party build is gone and
overlays/dev-tools/strictdoc.nix now re-exports upstream's OWN flake package
unchanged, on the same plain-attrset-update contract as overlays/semble.nix.
The STATEMENT above therefore describes a shape that no longer exists; see
MECH-STRICTDOC-UPSTREAM-FLAKE in the plan backlog for the grooming question
that raises, and MECH-STRICTDOC-VERSION-SMOKE for what the switch cost.

What changed and what it settles. Upstream's flake is a uv2nix set built from
the repository's own uv.lock, which pins every Python dependency to the exact
artifact the release was tested against, so BOTH dependency adjustments are
dead rather than merely unnecessary here: reqif comes from uv.lock at the
version the constraint wants, and pygments needs no relaxation because nothing
is resolving it against a nixpkgs pin. The sidecar, the tagPrefix = "" wrinkle,
the meta.changelog repointing and the update-targets row all went with them.
The update owner is now passthru.updateFlakeInput = "strictdoc", which
checks.update-targets-parity accepts and the ordinary flake-input sweep serves
(config/generate-update-ninja.nix derives its targets from flake.lock, so the
input needed no registration anywhere).

The cache-hit-parity row stays and still holds. It now holds TRIVIALLY -- the
derivation closes over upstream's locked nixpkgs, so its store path cannot vary
with a consumer's pin -- but a row that passes for a structural reason is still
what would catch a later edit reintroducing a final-bound wrapper, so it was
not removed.

One thing the switch DID force, and it is the only consumer that noticed. The
package is mkApplication over a virtual environment: $out holds bin/strictdoc
and nothing else -- no interpreter, no site-packages -- and its `dependencies`
is a uv2nix name-to-extras ATTRSET, not nixpkgs' list of derivations.
overlays/dev-tools/strictdoc-grammar-extract.nix consumed both of those, so it
could not survive unchanged; it now wraps the venv interpreter named by that
script's shebang, with ast_grep_py spliced onto PYTHONPATH from ourPkgs.
MEASURED: upstream's interpreter is 3.14.6 against ourPkgs' 3.14.7, the splice
imports clean, and the grammar builder returns the same 4adcdb05... grammar the
implementation brief records.
<<<
RELATIONS:
- TYPE: Parent
  VALUE: DEC-EXECUTABLE-RULES-ROADMAP
  ROLE: Governed_By
- TYPE: Parent
  VALUE: SPIKE-EXECUTABLE-RULES
  ROLE: Proven_By

[SLICE]
UID: SLICE-GRAMMAR-FROM-NIX
TITLE: Generate the grammar from a typed Nix option surface, and gate it
DEPTH: implemented
AUTHORED_BY: llm
STATEMENT: >>>
Generate a typed Nix option surface from strictdoc's own grammar definition,
and generate docs/sdoc/grammar.sgra from that surface. The surface is derived,
not hand-written: nothing about what a grammar may contain is typed by a
person.

Two layers. The first is faithful -- it expresses exactly what a .sgra file can
express, with no opinion of ours in it. The second is normalized: named
converters turn faithful shapes into better Nix types, so a regex that is a
pure literal alternation becomes an enum, a two-value alternation becomes a
boolean, an optional group becomes a nullable with a null default. A shape no
converter recognises is an error rather than a fallback to free text, so an
upstream grammar change fails during the update sweep instead of reaching
anyone. Declaring a value unconstrained is itself a converter, keeping "we
decided this is free text" distinguishable from "we did not recognise this".

The extractor runs at generation time, outside Nix, and emits Nix source that
is committed; Nix never parses strictdoc during evaluation. A drift check
regenerates and diffs, so a stale surface is a red check.

How the conversion is expressed is open. Two shapes, both viable, and the
choice decides whether the faithful layer is a committed file.

Converters can live inside the extractor, working on the parsed grammar. That
preserves why each shape was classified as it was: a pattern is known to have
come from a particular grammar rule rather than inferred from how it rendered.

Or the extractor emits the faithful surface and a declarative rewrite
transforms it. Measured: ast-grep is tree-sitter based and ships a Nix grammar,
so it parses our shapes with nothing added; a rule of about fifteen lines turns
a literal-alternation pattern into an enum; and the fail-closed condition is
one more catch-all rule at error severity rather than a special case in code.
Both the tool and its Python bindings are packaged already, and the bindings
work on Nix source in process, so this needs no second toolchain and no
separate file format -- the rewrite can live in the same script as the
extraction.

The remaining cost of the second shape is provenance, and it is the whole
argument. It matches generated text rather than the grammar behind it, so a
two-value alternation that means a boolean is indistinguishable from one that
merely looks like it.

Our own grammar values -- the five node types with their fields and relations
-- are data filling the generated surface, not part of it.

Add the validation gate: a clean-directory strictdoc export over the whole
corpus at commit time and in CI. This is not a second opinion. None of
strictdoc's grammar checks run on a bare parse, so the corpus export is the
only validation that ever happens to a generated grammar.

What belongs at evaluation is only what strictdoc has no rule for anywhere: two
fields with the same title, and two relations with the same type and role.
Both are made unrepresentable by keying on name rather than asserted against.
Everything strictdoc does enforce is left to strictdoc and becomes a negative
fixture proving the gate fires.

Consumer surface the operator reviews before implementation: the normalized
option tree and the converter list. Reviewed after: the regenerated grammar as
an empty diff, the gate firing on a deliberately broken fixture, and an
unrecognised grammar shape failing the extractor.

Not included: behaviour, transitions, ownership rules, which fields count as
contract, which node types a relation may point at, and any ordering policy of
ours. Those are the semantic layer, defined by a consumer of this surface
rather than by it.
<<<
RATIONALE: >>>
Generating rather than hand-writing is the operator's call, and the reason is
drift: the overlay now tracks a project shipping roughly three releases a
month, and a hand-written surface does not notice a knob being added. It keeps
generating a valid grammar that cannot express the new thing, with nothing
going red.

Measured, and it is derivable: strictdoc assembles its own grammar into a
string that is byte-identical across the last two releases; a metamodel built
from it reaches 25 of 43 rules from the root, and its abstract rules yield the
four field types and three relation types without a list being typed by hand --
including that file relations have no reverse role at all. The metamodel alone
is not sufficient, reporting every attribute as mandatory and flattening value
vocabularies, so optionality and literal sets come from the parser tree beneath
it. Both are reachable from the same object.

Also measured, and the reason two checks stay at evaluation: a grammar
declaring one field twice and one relation twice exports clean with exit zero,
and the duplicates resolve in opposite directions -- fields keep the last
declaration, relations keep the first. No rule against either exists anywhere
in strictdoc.

Carried from the spike: a typed surface regenerates the grammar byte-for-byte
in 0.03 s and rejects thirteen of thirteen bad declarations once the merged
value is forced; strictdoc rejects six of six injected grammar defects; the
gate needs nothing but the strictdoc package; and cross-field checks must live
in one place that forces evaluation of the whole value, because Nix's addCheck
never runs on a nested option.
<<<
PARENT_FP: >>>
DEC-EXECUTABLE-RULES-ROADMAP:0000000
DEC-FP-FIELDS-CONFIGURABLE:0000000
<<<
NOTES: >>>
The faithful layer carries every native grammar feature by construction, so
nothing needs listing as a deliberate inclusion. What the NORMALIZED layer
exposes is a scoping decision and is open below.

What the implementation settled, each of which had been left open here:

Element order is carried by the VALUES. Elements, fields and relations are all
lists, never attribute sets, because Nix sorts attribute-set keys and strictdoc
enforces order -- so the conceptual order survives and no reshuffle was needed.
The consequence is that duplicate detection is an explicit assertion rather than
a structural side effect, which is why the two duplicate checks exist at all.

Both layers are materialised as committed files, and the component is general
purpose: the normalized layer carries every native grammar feature, including
the composite nodes, view styles, human titles, child relations and file roles
this repository never uses. Those are exercised by
packages/strictdoc-grammar/fixtures/foreign.nix, which round-trips
byte-identically, and the five node types are one consumer in
packages/strictdoc-grammar/values.nix rather than part of the surface.

Two corrections the extraction needed, both found by running the chain:

A '^'-anchored negative lookahead is POSITIONAL, not a value constraint.
FieldName is /(?!^UID)(?!^RELATIONS).../ and arpeggio matches with re.MULTILINE
at the current position, so the lookahead can only fire at a line start -- which
a field title, sitting after the literal '  - TITLE: ', never is. Hoisting those
two into a value-level denial produced a type that rejected a field named UID,
which this repository's own grammar declares five times. They are now recorded
under denyAtLineStart and not enforced.

The choice vocabulary could not keep its upstream name. textx calls it options,
and a submodule whose CONFIG carries a key named options is read by the Nix
module system as an option DECLARATION, so every sibling key errors out. The
extractor now renames reserved module-system attribute names, and a collision
with no rename is fatal rather than silent.

WHAT CLOSES THIS SLICE, ruled by the operator 2026-08-26. The slice is
implemented but not accepted, and these three stand between:

  MECH-STRICTDOC-DEVENV-MODULE -- an ai.strictdoc module owning the wrapping and
    the grammar generation, with enable, package and grammars.
  MECH-GRAMMAR-EXTRACT-SOURCE-BOUNDARY -- strip the wrapped environment out of
    the overlay; the overlay converts, the module wraps.
  MECH-STRICTDOC-UPSTREAM-FLAKE -- take strictdoc from upstream's own flake and
    retire the step-zero overlay, accepting that it tracks main.

Settled at the same time and no longer open here: docs/sdoc/grammar.sgra IS
generated, through that module, as this repository's convention rather than a
constraint on consumers. Contract-bearing fields are semantic and their edge
leaves this slice -- see MECH-CONTRACT-FIELDS-EDGE-TO-SEMANTIC-LAYER; the
PARENT_FP entry moves with it and only the operator changes those. HTML
rendering becomes a requirement of its own rather than a property of this
slice, tracked as MECH-HTML-RENDER-MUST-PASS.

Still needing a round with the operator before they can be closed: whether the
grammar gates belong in the flake checks output, whether the emitter should stay
reachable without the type in front of it, and whether the line-anchored
denials recorded above are enforced anywhere. None of the three blocks the
three closure items above.
<<<
RELATIONS:
- TYPE: Parent
  VALUE: DEC-EXECUTABLE-RULES-ROADMAP
  ROLE: Governed_By
- TYPE: Parent
  VALUE: DEC-FP-FIELDS-CONFIGURABLE
  ROLE: Governed_By
- TYPE: Parent
  VALUE: MECH-SDOC-CI-CHECK
  ROLE: Crosses
- TYPE: Parent
  VALUE: MECH-TREEFMT-SDOC
  ROLE: Crosses
- TYPE: Parent
  VALUE: MECH-SDOC-LEAN-FORMATS
  ROLE: Crosses
- TYPE: Parent
  VALUE: SLICE-STRICTDOC-OVERLAY
  ROLE: Assumes
- TYPE: Parent
  VALUE: SPIKE-EXECUTABLE-RULES
  ROLE: Proven_By

[SLICE]
UID: SLICE-SDOC-CLI
TITLE: A command-line tool that is the only writer of sdoc files
DEPTH: needs-design
AUTHORED_BY: llm
STATEMENT: >>>
Build the tool through which every node is created and changed: create, set,
relate and move, with flags derived from the generated grammar (fields,
choices, relation roles); UIDs minted through strictdoc's own hook; required
fields filled from arguments so a TBD never lands; every write validated
against the whole graph as it would be after the write, before the file is
replaced; formatting applied by the same code path. Deny direct edits of sdoc
and grammar files in the agent harness, before the edit tool runs, and point
the model at the tool. No lifecycle verbs yet: this milestone is create, read,
update and delete.

Consumer surface the operator reviews before implementation: the verb list
and their flags. Reviewed after: a session that authors nodes through the
tool only, and a direct edit being refused.
<<<
RATIONALE: >>>
In the operator's words, the root failure is a model producing incorrect
formats with nothing validating the write; the tool takes the model's hands
off the files. Measured: creating a node in-process costs 0.35 s, validating
the whole graph 0.3 s, and strictdoc's node model writes any field in grammar
order -- nothing here waits on the behaviour model.
<<<
PARENT_FP: DEC-EXECUTABLE-RULES-ROADMAP:0000000
NOTES: >>>
Build on strictdoc's own machinery rather than re-implementing writes: manage
new for scaffolding, set_field_value for fields, the writer for formatting.
The cache directory must live outside the checkout for worktrees. Validating
the whole graph per command costs about a second on this corpus and about
two at five thousand nodes when strictdoc's cache is warm, which needs the
working copy at a stable path; a fresh temporary copy pays the cold cost.
<<<
RELATIONS:
- TYPE: Parent
  VALUE: DEC-EXECUTABLE-RULES-ROADMAP
  ROLE: Governed_By
- TYPE: Parent
  VALUE: MECH-RUNTIME-WRITE-GUARD
  ROLE: Crosses
- TYPE: Parent
  VALUE: MECH-SDOC-EDIT-VIA-MODEL
  ROLE: Crosses
- TYPE: Parent
  VALUE: MECH-SDOC-LEAN-FORMATS
  ROLE: Crosses
- TYPE: Parent
  VALUE: MECH-SDOC-CACHE-DIR-FOR-WORKTREES
  ROLE: Crosses
- TYPE: Parent
  VALUE: MECH-FILE-RELATION-EXISTENCE
  ROLE: Crosses
- TYPE: Parent
  VALUE: SLICE-GRAMMAR-FROM-NIX
  ROLE: Assumes
- TYPE: Parent
  VALUE: SPIKE-EXECUTABLE-RULES
  ROLE: Proven_By

[SLICE]
UID: SLICE-BEHAVIOUR-MODEL
TITLE: Define the behaviour model in Nix and render it for review
DEPTH: needs-design
AUTHORED_BY: llm
STATEMENT: >>>
Define, as a typed Nix option tree layered over the grammar:

- the lifecycle of each node type: its states over grammar fields, the legal
  moves, who may make each move, what each move writes;
- triggers: a command, an outside event such as landing in main, a timer,
  another move finishing;
- gates and invariants, each declaring what it needs to see, so that the
  places it can run are derived rather than declared;
- relation contracts: which node types a role may point at, whether cycles
  are allowed, whether a change propagates across the relation;
- flows.

Cross-check every value against the grammar at evaluation. From one
evaluation emit a machine-readable model for the tool and the validators, a
state diagram per node type, a diagram per flow, a table of moves against
gates, a table of gates against where they can run, and a report of what is
still only prose.

Consumer surface the operator reviews before implementation: the option tree
and the rendered diagrams -- this is where the node lifecycle becomes
something to look at rather than guess at. Three shape questions are open and
are brought one at a time before the surface is fixed: whether state is one
machine per field or one machine over all of a node's state fields at once;
whether the ripple -- what goes stale when a node changes -- is derived from
declared read and write scopes or from a per-field contract flag; whether a
flow is a list of move references or a step-by-step script. Reviewed after:
the diagrams and tables regenerate from one evaluation, and the rendered
lifecycle matches the graph as it stands.
<<<
RATIONALE: >>>
Every part of this was prototyped in the spike and its review: both state
shapes, four representations of gate placement that all derive the same
result -- including that the authorship guard can run nowhere today -- flows
that drift when they restate moves, and eight rendered views from one
evaluation.
<<<
PARENT_FP: >>>
DEC-EXECUTABLE-RULES-ROADMAP:0000000
DEC-LOCAL-IMPLEMENTABILITY:0000000
<<<
NOTES: >>>
Vocabulary adopted from the outside research: a command is a request and may
be refused; an event is an accepted fact; a milestone is an achieved fact that
can go stale; a gate's evidence records what it depended on. The instance's
signed edge is carried as evidence that can go stale rather than as a node
type of its own -- contested in review, settled when the surface is fixed.
<<<
RELATIONS:
- TYPE: Parent
  VALUE: DEC-EXECUTABLE-RULES-ROADMAP
  ROLE: Governed_By
- TYPE: Parent
  VALUE: DEC-LOCAL-IMPLEMENTABILITY
  ROLE: Governed_By
- TYPE: Parent
  VALUE: MECH-READY-QUERY
  ROLE: Crosses
- TYPE: Parent
  VALUE: MECH-READINESS-PREDICATE-RECONCILE
  ROLE: Crosses
- TYPE: Parent
  VALUE: MECH-RELATION-TARGET-TYPE-LINT
  ROLE: Crosses
- TYPE: Parent
  VALUE: SLICE-GRAMMAR-FROM-NIX
  ROLE: Assumes
- TYPE: Parent
  VALUE: SPIKE-EXECUTABLE-RULES
  ROLE: Proven_By

[SLICE]
UID: SLICE-CHECKPOINT-WIRING
TITLE: Wire the behaviour model into the tool and the checkpoints
DEPTH: needs-design
AUTHORED_BY: llm
STATEMENT: >>>
Add the lifecycle verbs to the tool: a move is a command that selects one
transition, checks its gates, and either refuses with a diagnostic or writes.
Register the existing checks -- fingerprint drift, cycles, plan boundaries,
the authorship guard -- as validators at the checkpoints the model derives for
them: the command before and after its write, the pre-commit hook against the
previous commit, CI against the point where the branch left main, and
strictdoc's own read-time and after-parse hooks as backstops for edits that
bypass the tool. Surface every gate that has no validator, or no checkpoint
able to see what it needs; whether that fails the evaluation or only reports
is settled at review. One such gate is known already: the authorship guard
needs both git history and who is acting, and no checkpoint sees both, so it
is recorded as unenforceable until agents have their own identity (milestone
five).

Consumer surface the operator reviews before implementation: the checkpoint
table -- which check runs where, and what is still unenforceable. Reviewed
after: a rule that used to live in the skill being refused by a running check.
<<<
RATIONALE: >>>
This is the milestone INV-GUARDS-MUST-EXECUTE asks for. Measured: strictdoc's
after-parse hook never runs when a node is created, so it is a backstop; its
read-time hook fires on every command; checks that need the previous state
cannot run at command time by construction; checks that need to know who is
acting can run only in the acting session until agents have their own
identity.
<<<
PARENT_FP: DEC-EXECUTABLE-RULES-ROADMAP:0000000
NOTES: >>>
A flow's tests become its contract once its mechanics settle, per
MECH-TESTS-AS-CONTRACT.
<<<
RELATIONS:
- TYPE: Parent
  VALUE: DEC-EXECUTABLE-RULES-ROADMAP
  ROLE: Governed_By
- TYPE: Parent
  VALUE: MECH-SDOC-CI-CHECK
  ROLE: Crosses
- TYPE: Parent
  VALUE: MECH-FP-CHECK
  ROLE: Crosses
- TYPE: Parent
  VALUE: MECH-CYCLE-CHECK
  ROLE: Crosses
- TYPE: Parent
  VALUE: MECH-PLAN-REFS-CHECK
  ROLE: Crosses
- TYPE: Parent
  VALUE: MECH-AUTHORED-BY-GUARD
  ROLE: Crosses
- TYPE: Parent
  VALUE: MECH-TESTS-AS-CONTRACT
  ROLE: Crosses
- TYPE: Parent
  VALUE: SLICE-SDOC-CLI
  ROLE: Assumes
- TYPE: Parent
  VALUE: SLICE-BEHAVIOUR-MODEL
  ROLE: Assumes
- TYPE: Parent
  VALUE: SPIKE-EXECUTABLE-RULES
  ROLE: Proven_By

[SLICE]
UID: SLICE-INSTANCE-SEMANTICS-MIGRATION
TITLE: Migrate this system's own semantics onto the plumbing
DEPTH: needs-design
AUTHORED_BY: llm
STATEMENT: >>>
Express this system's own semantics in the behaviour model and retire the
hand-written scripts they live in today: which fields count as a node's
contract; a signed edge as evidence that goes stale when the parent's
contract changes; readiness -- everything a node depends on is settled -- and
its count of open decisions as gates; signing and the authorship flip as moves
with a rule about who may make them; revocation made visible. The two keys
stay separate: an independent session marks a node verified, and only the
operator claims authorship. The decisions this milestone needs are the
instance's own -- who may sign, whether DEPTH may move backwards, whether
implemented and verified belong in DEPTH, agent identity -- and are taken at
its review, not before.

Consumer surface the operator reviews before implementation: the instance's
lifecycle rendered from the model, with those decisions marked. Reviewed
after: the existing fingerprint and readiness checks pass through the new
validators with identical results on the real graph.
<<<
RATIONALE: >>>
Migration last keeps the open instance decisions from blocking the plumbing,
and the plumbing is what makes those decisions reviewable rather than guessed.
<<<
PARENT_FP: >>>
DEC-EXECUTABLE-RULES-ROADMAP:0000000
DEC-FINGERPRINT-IN-NODE:0000000
DEC-FP-ACCEPT-AUTHORITY:0000000
<<<
NOTES: >>>
Git-flow handling -- rebase, squash lineage, pre-merge collection -- stays
deferred until a branch reaches main, per MECH-FP-GIT-FLOW-HAZARDS.
<<<
RELATIONS:
- TYPE: Parent
  VALUE: DEC-EXECUTABLE-RULES-ROADMAP
  ROLE: Governed_By
- TYPE: Parent
  VALUE: DEC-FINGERPRINT-IN-NODE
  ROLE: Governed_By
- TYPE: Parent
  VALUE: DEC-FP-ACCEPT-AUTHORITY
  ROLE: Governed_By
- TYPE: Parent
  VALUE: MECH-FP-CHECK
  ROLE: Crosses
- TYPE: Parent
  VALUE: MECH-FP-ACCEPT-READINESS
  ROLE: Crosses
- TYPE: Parent
  VALUE: MECH-SIGNATURE-REVOCATION
  ROLE: Crosses
- TYPE: Parent
  VALUE: MECH-AGENT-IDENTITY-KEYS
  ROLE: Crosses
- TYPE: Parent
  VALUE: MECH-FP-MAIN-LINEAGE
  ROLE: Crosses
- TYPE: Parent
  VALUE: SLICE-CHECKPOINT-WIRING
  ROLE: Assumes
- TYPE: Parent
  VALUE: SPIKE-EXECUTABLE-RULES
  ROLE: Proven_By
