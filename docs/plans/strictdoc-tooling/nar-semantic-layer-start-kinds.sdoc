[DOCUMENT]
TITLE: The seven kinds of node

[GRAMMAR]
IMPORT_FROM_FILE: @repo

[NARRATIVE]
UID: NAR-SEMANTIC-LAYER-START-KINDS
TITLE: The seven kinds of node
AUTHORED_BY: llm
WIDGET: grid
PLACE: screen
STATEMENT: >>>
Ruled on 2026-08-28 and re-ruled on 2026-08-30: node types come from two questions -- does it say how the world ought to be or how it is, and is it about every case or one case. Tap a cell.
<<<
RELATIONS:
- TYPE: Parent
  VALUE: NAR-SEMANTIC-LAYER-TYPES-GRID
  ROLE: Over
