[DOCUMENT]
TITLE: Authorship is one monotonic field, and it governs reversal rather than credit

[GRAMMAR]
IMPORT_FROM_FILE: @repo

[DECISION]
UID: DEC-AUTHORSHIP-LADDER
TITLE: Authorship is one monotonic field, and it governs reversal rather than credit
AUTHORED_BY: llm
STATUS: accepted
RETIRES_ON: A reversal case appears that the three values cannot distinguish, or the ladder needs to run backwards.
STATEMENT: >>>
Authorship is tracked on every node, as ONE field on a MONOTONIC ladder, and
what it governs is REVERSAL rather than credit.

  llm              written by a model
  human-adopted    a human has taken model-written words on as their own
  human            written by a human

The treatment reads off the value, two classes over three values:

  llm                    FREE. A model may reverse it without asking.
  human-adopted, human   HARD. A model may not reverse it. Being unable to
                         meet it is a STOP condition: raise it with the human
                         rather than working around it.

human-adopted and human differ in LINEAGE, which is why they share a
treatment. The ladder is one-directional: a value may rise and never fall, so
there is no reachability question and no way to launder a human commitment back
into a free one.

WHAT THIS IS NOT. It is not attribution and not credit. It is the guard on the
reverse edge -- the answer to "who is allowed to undo this, and what do they owe
if they do." That is why it costs one field rather than an actor model: it
parameterises an undo that already exists instead of adding an axis.
<<<
RATIONALE: >>>
The operator asked for authorship to be tracked even where nothing consumes it
yet, on the grounds that a view over it is interesting on its own and carrying
an unused field costs nothing. That is cheap to honour and expensive to
retrofit, since the value has to be recorded when the node is written and cannot
be recovered afterwards.

One field rather than two -- provenance plus a separate human stance -- because
the three meaningful states form a ladder. Two fields would be a product with
unreachable corners.
<<<
COMMENT: >>>
Corrected in place on 2026-09-10 under the operator's ruling that wrong accepted decisions on this branch are corrected rather than superseded. The ladder changed from four rungs to llm, human-adopted and human because merely seeing model-written words and letting them stand is not authorship: adoption means a human has taken those words on, while human means a human wrote them. The writer still stamps llm and exposes no AUTHORED_BY flag. Who may raise a value remains open; raising to human-adopted is a human act with no natural place to happen yet. The stop condition belongs in L3, not in the field.
<<<
