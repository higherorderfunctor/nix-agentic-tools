[DOCUMENT]
TITLE: StrictDoc tooling plan backlog

[GRAMMAR]
IMPORT_FROM_FILE: @repo

[DECISION]
UID: DEC-PLAN-SCOPED-BACKLOG
TITLE: Each plan carries its own backlog document, and no new node type
AUTHORED_BY: human
STATUS: accepted
RETIRES_ON: >>>
An item needs to be tracked while living outside its plan's backlog document,
at which point an explicit register node and a Backlogged_In role become the
cheaper answer.
<<<
STATEMENT: >>>
Every plan directory may hold a 99-backlog document. Anything noticed but not
groomed goes there as an ordinary node at DEPTH sketch. Grooming means moving
the node into a numbered document in the same plan and raising its DEPTH; the
UID never changes, so nothing that cites it breaks.

The plan's ungroomed set is therefore the query DEPTH == sketch scoped to that
plan's directory. Debt remaining when a plan closes is whatever is still at
sketch, and what to do with it is not decided here.
<<<
RATIONALE: >>>
A dedicated BACKLOG node type was considered and rejected. The existing types
already say what kind of work an item is -- a MECHANISM to build, a DECISION to
make, a SPIKE to run -- and a separate type would throw that away and need
mapping back on grooming. Containment by document needs no grammar change at
all, and DEPTH sketch already means exactly ungroomed.
<<<
NOTES: >>>
Deliberately not solved here: a repo-level backlog above plans. That decision
waits for a plan to actually close with debt on it.
<<<

[DECISION]
UID: DEC-LOG-DONT-SURFACE
TITLE: Incidental findings go to the backlog, not to session output
AUTHORED_BY: human
STATUS: accepted
RETIRES_ON: >>>
The backlog grows faster than it is groomed, which would mean the filter is
letting too much through and the threshold needs restating.
<<<
STATEMENT: >>>
A model working in this repository may add backlog nodes on its own initiative,
without asking. It should.

Session output raises a finding only when it matters SOON -- it changes the
decision in front of the operator, or it blocks the work in hand. Everything
else, the whole class of "one more thing you should know", is written to the
plan's backlog document and not spoken. A finding that is logged is not lost, so
mentioning it costs attention while logging it costs nothing.

This applies to planning and implementation sessions alike.
<<<
RATIONALE: >>>
The operator's judgment budget is the scarce resource, not disk or tokens.
Surfacing everything spends that budget on things that are not urgent, and the
predictable result is that genuinely urgent findings get skimmed along with the
rest.
<<<

[MECHANISM]
UID: MECH-TREEFMT-SDOC
TITLE: Register strictdoc format as the treefmt formatter for sdoc and sgra
DEPTH: interface-settled
AUTHORED_BY: human
STATEMENT: >>>
treefmt formats no file with an sdoc extension today: none of its five formatters -- alejandra, biome, prettier, shfmt, taplo -- claims one, and an unmatched path is logged at info while the run still exits zero. Register strictdoc format as treefmt's formatter for *.sdoc, and set document_line_width = 80 in strictdoc_config.py so that the command has something to enforce. Without the width the command normalises nothing a reader can see: measured, every deviation short of a parse error round-trips unchanged, so a formatter registered without it is a validator wearing a formatter's name.

The wiring is one settings.formatter.strictdoc entry with includes = ["*.sdoc"] whose command is a writeShellApplication carrying pkgs.ai.devTools.strictdoc. treefmt.nix becomes a {pkgs, ...}: module to reach that package; both of its consumers already supply pkgs as a module argument, so no other file changes shape.

The wrapper does not format in place. It mirrors strictdoc_config.py, .gitignore and every .sdoc and .sgra file into a temporary directory, runs strictdoc format . there, and copies back only the paths treefmt named, and only those whose bytes differ. That indirection is what pays for the awkward fit, and both halves of it are load-bearing. format takes one project directory and rewrites every document under it unconditionally, changed or not, so formatting in place advances the mtime of every document in the tree; treefmt decides a file changed by size and mtime, so --fail-on-change would then fail on every run over a byte-identical corpus. And the pre-commit hook passes filenames, so a commit-time run is handed only the staged paths -- an in-place run would silently reformat unstaged documents while treefmt, which stats only what it emitted, reported the run clean.

*.sgra is explicitly OUT, and not merely deferred. strictdoc format never writes one: it reads a grammar to parse documents, and its writer loop covers .sdoc and .md only. Both .sgra files in this repository already have a writer -- docs/sdoc/grammar.sgra is written by the generate:sgra devenv task from ai.strictdoc.grammars.repo and gated by checks/strictdoc-grammar-model-equal.nix, and packages/strictdoc-grammar/fixtures/foreign.sgra is a round-trip fixture whose bytes are the assertion. Registering a formatter over either would put a second writer on a generated file.

Also out, and permanently rather than as a later optimisation: any narrowing of what runs. format accepts exactly one positional path, and resolving the @repo grammar alias against anything narrower than the project root fails, --config included, because the alias is validated against the input path rather than against the config's directory. One invocation per treefmt batch, each formatting the whole tree, is the only mode there is.
<<<
RATIONALE: >>>
Two things depend on canonical form. Fingerprints are taken over field text, so an unformatted file hashes differently from the same content formatted. And the commit gate runs treefmt with fail-on-change, so anything treefmt does not know about cannot be enforced there.

Both reasons require a width. contract_hash serialises the node's raw field values, newlines included, so what a fingerprint signs is the wrapping as typed; and fail-on-change can only enforce a rule the formatter actually applies. With document_line_width unset there is no such rule, which is why the width is part of this mechanism rather than a separate preference.

The sandboxed copy is not defensiveness about a hypothetical. Both failures it prevents were reproduced: an in-place wrapper made treefmt report all nine documents changed on a corpus it had just left byte-identical, and an in-place run given a single path reformatted a different, unstaged document while treefmt reported zero changes.
<<<
NOTES: >>>
Measured 2026-08-27 against strictdoc 0.28.3 and treefmt 2.5.0, on a copy of the corpus outside the repository.

THE MID WARNING DOES NOT REPRODUCE, and the mechanism says why it cannot. strictdoc format . over the whole corpus leaves all nine .sdoc files byte-identical and adds no MID to any of them; no file in the corpus carries one. The writer emits MID only when document.mid_permanent or document.config.enable_mid holds, and mid_permanent is set from `mid is not None` at parse -- that is, only for a document that already declared one in its source. ENABLE_MID is not a lever that could be tripped by accident either: setting it on a probe document made the export fail with "Grammar element 'DECISION' is missing the MID field which contradicts to the DOCUMENT's ENABLE_MID setting", so it additionally requires a MID field on every grammar element. The observation behind the warning most likely came from `manage new`, whose own comment says it sets mid_permanent so the writer persists a MID -- and even there only when enable_mid is set. Positive control that the harness would have seen minting: the same before/after comparison detects a 93-line reflow, and detects a one-word edit under the whitespace-insensitive comparison used below.

WHAT FORMAT ACTUALLY NORMALISES WITHOUT A WIDTH: nothing observable. A paragraph de-wrapped to a single 120-character line survives format . unchanged. Single-line and >>>-delimited forms of the same field are both preserved. The deviations that do get corrected are the ones the parser rejects outright -- a double blank line between blocks fails with "Expected EOF" rather than being repaired. So the statement that the corpus is a no-op "because the files were written in canonical form by hand" is true by the wrong mechanism: nothing was being enforced.

THE ONE-TIME COST OF SETTING document_line_width = 80. Five of the nine documents reflow, 93 changed lines in total: 00-approach 6, 01-tooling 27, 02-plan-lifecycle 7, 99-backlog 47, packages/semble/.sdoc/01-grammar-injection 6. Every one of the five is whitespace-only -- collapsing runs of spaces and newlines gives an identical byte stream before and after, and that comparison does detect a planted one-word change. A second run is byte-identical, so it converges in one pass. The corpus is not currently at 80 by hand: maximum line lengths run 80, 81, 82, 85, 86, 99, 100, 111 and 349. strictdoc's wrapper leaves an over-long unbreakable token overflowing rather than splitting it, the same way prettier's proseWrap does, so 82-character lines survive legitimately.

The reflow costs no fingerprint today and will not stay free. fp-check over the current export reports 31 fingerprint entries, 0 signed and current, 31 never signed. Every signature taken before this lands would drift the moment it does, so it belongs ahead of the first fp-accept rather than after it.

TREEFMT DECIDES BY MTIME. Its diagnostic prints prev_size and current_size and they were equal for every file it flagged -- the reflow swaps a space for a newline and the byte count does not move -- so mtime is the discriminator. Two runs pin it down: an in-place wrapper produced "formatted 9 files (9 changed)" and failed --fail-on-change over a corpus whose bytes it had not altered; the same wrapper with the original mtime restored on every unchanged file produced "0 changed" and exit 0.

COLLATERAL WRITES ARE REAL AND SILENT. devenv's git-hooks treefmt hook is defined with pass_filenames = true. Running treefmt on one path, with a different document left non-canonical, reformatted that other document and reported "1 files (0 changed)": treefmt stats only what it emitted, so the working tree moved and the gate stayed green. The sandboxed copy is what closes this; it reproduces the in-place width-80 result byte for byte while touching only the named paths.

THE DIAGNOSTIC GOES TO STDOUT. strictdoc prints its parse and semantic errors on stdout, not stderr, so a wrapper ending in `strictdoc format . > /dev/null` swallows every error message while still exiting 1. Measured with a deliberately broken document, treefmt then reports only "failed to apply with options '[]': exit status 1", formats nothing in that batch, and exits non-zero. Fail-closed, but useless to read: keep the output, or redirect stdout to stderr.

TWO SIDE EFFECTS THAT MUST NOT LAND IN THE TREE. format writes output/_cache/<version>/ (2.4 MB on this corpus) into the current directory -- it has no --output-dir -- and importing strictdoc_config.py leaves a __pycache__ beside it. Inside the temporary directory both are discarded with it. If a future in-place path is ever wanted, dir_for_sdoc_cache in strictdoc_config.py does relocate the cache (verified: the tree root stayed clean and the cache appeared at the configured absolute path), which is the same lever MECH-SDOC-CACHE-DIR-FOR-WORKTREES describes; PYTHONDONTWRITEBYTECODE=1 suppresses the other.

MIRROR THE .gitignore TOO. project_config reads the project's .gitignore and extends exclude_doc_paths with its patterns, so a copy without it has a different document set from the real tree.

A TRAP IN THE FILE LIST: packages/semble/.sdoc is a DIRECTORY whose name ends in .sdoc, so `find -name '*.sdoc'` matches it. Use -type f.

COST. The wrapper runs in 1.84 s warm against 1.81 s for a bare in-place format, so mirroring 12 files costs about 30 ms. treefmt invokes the command once per batch and nine files is one batch. strictdoc is already in CI's build closure -- checks/strictdoc-fp-check.nix takes pkgs.ai.devTools.strictdoc as a nativeBuildInput -- so registering it here adds nothing to what checks.formatting must build, even though the devenv shell keeps ai.strictdoc.enable = !isCI.
<<<

[MECHANISM]
UID: MECH-SGRA-BODY-COVERAGE
TITLE: Extend the sdoc tree-sitter grammar to cover document-body content
DEPTH: sketch
AUTHORED_BY: llm
STATEMENT: >>>
Measured while implementing SLICE-SDOC-IN-SEMBLE:
checks/strictdoc-grammar-corpus.nix parses strictdoc-project/strictdoc's own
docs/ (15 files, pinned rev 215cda2e) and gets 5/15 clean under the patched
grammar, unchanged from baseline. The 10 failures are unrelated to
DEC-GRAMMAR-PATCH-NOT-FORK's patch (root-rule choice + REVERSE_ROLE) -- they
are document-body / FREETEXT coverage gaps in the upstream grammar itself,
present before and after this patch.
<<<
RATIONALE: >>>
Out of scope for the current patch, which targets exactly the two bugs this
repository's own corpus hit. Worth a dedicated SPIKE to characterize the
FREETEXT gap before deciding whether it is a small follow-up patch or a
reason to look upstream harder.
<<<

[DECISION]
UID: DEC-LONG-LIVED-BRANCH
TITLE: Work accumulates on one long-lived branch, restacked into pull requests later
AUTHORED_BY: human
STATUS: accepted
RETIRES_ON: >>>
The first restack completes and the branch merges, at which point the next unit
of work chooses its own shape.
<<<
STATEMENT: >>>
No pull request is opened during development and none is offered. Work
accumulates on one branch until the operator calls a milestone, then it is
restacked into a series of reviewable pull requests.

Two reviews, with different subjects. The stack is reviewed as a whole for
usability, design and flow. The pull requests are reviewed for implementation
choices. Operator acceptance is turned at the second of these, never before.
<<<
RATIONALE: >>>
Commit boundaries are what make the restack legible, which is why worker
sessions commit per unit of work rather than once at the end. And there is no
signature to turn yet: the fingerprints are placeholders until the suspect-link
check exists, so acceptance has nothing to attach to before then.
<<<

[SLICE]
UID: SLICE-RESTACK-TO-PRS
TITLE: Restack the long-lived branch into reviewable pull requests
DEPTH: sketch
AUTHORED_BY: human
STATEMENT: >>>
Cut the accumulated branch into a series of pull requests ordered so each is
independently reviewable, and land them.
<<<
RATIONALE: >>>
Slotted as future work so the strategy is tracked rather than remembered. Not
groomed: the cut points depend on what has accumulated by the milestone.
<<<
RELATIONS:
- TYPE: Parent
  VALUE: DEC-LONG-LIVED-BRANCH
  ROLE: Governed_By

[MECHANISM]
UID: MECH-AUTHORED-BY-GUARD
TITLE: Reject an AUTHORED_BY flip on a node already merged to main
DEPTH: interface-settled
AUTHORED_BY: human
STATEMENT: >>>
A static check over committed trees that reports every node claiming
AUTHORED_BY: human, classified by what a baseline tree said about the same node.

Build a map of UID to AUTHORED_BY from every .sdoc file in a tree -- plans,
docs/spec, and the co-located packages/*/.sdoc alike -- and build it twice, once
at the baseline and once at the candidate. Key by UID across the whole tree,
never per file: grooming moves a node between files with its UID intact, and a
per-file or line-diff view reads that move as a fresh claim. Every node whose
candidate value is human falls into one of two classes. A FLIP is a node the
baseline carried as llm. A NEW-HUMAN is a node the baseline tree does not carry
at all. A flip fails the check; a new-human node is listed and does not.

The baseline is the merge base of the branch and origin/main, not origin/main's
tip. It attributes exactly the changes this branch made and is unmoved by main
advancing underneath a long-lived branch. It moves only when the branch rebases,
and then it moves forward past claims that have already reached main, which is
correct -- those are main's now, and re-reporting them would train the reader to
skip the report. On the branch's first restacked pull request the baseline
carries no .sdoc file at all, so every human node in it reports as new-human;
that is the intended reading of a first appearance, not noise to suppress.

The checkpoint is a CI job checked out with full history. It cannot be a nix
flake check: the flake source tree has no .git, so nothing running under nix
flake check can see a baseline. The same comparison may run in the pre-commit
hook against the previous commit, and there it is a convenience only -- the hook
suite is disabled under CI, and squash merge erases the per-commit record it
would produce.

Permanently out of scope on this side: who made the change. A committed tree
carries no evidence of the actor, so this check reports a claim and never
authorizes one. That is the line with MECH-RUNTIME-WRITE-GUARD, which sees the
actor and the write it is making and no history. Neither sees both, so an
entitled flip and an unentitled one are indistinguishable to either, and this
milestone therefore ships no override token: anything it could accept would be
forgeable by exactly the party the check guards against. Whether a failing check
blocks a merge is not settled here either -- promoting the job to a required
status check is a ruleset change, which only the operator can make.
<<<
RATIONALE: >>>
AUTHORED_BY is the operator's key, and the only thing standing against an agent
turning it is a rule in the authoring skill. INV-GUARDS-MUST-EXECUTE measured
that class: the sibling rule against editing PARENT_FP failed, and an agent
signed five contracts under the operator's committer identity. Something that
runs is what replaces guidance.

Detection without authorization is worth shipping on its own. The enforcement
actually available today is making every appearance of the operator's key
visible at the place acceptance is turned -- pull-request review, per
DEC-LONG-LIVED-BRANCH -- and a per-pull-request list of nodes claiming that key
is correct without knowing who acted. Withholding the mechanism until it can
also authorize leaves the key unwatched through all of milestones one to four,
and authorization waits on MECH-AGENT-IDENTITY-KEYS.

The comparison is UID-keyed against a merge base rather than a diff against main
because both cheaper readings are wrong in measured ways: a line diff cannot
distinguish a groom from a birth, and main's tip drifts for reasons that have
nothing to do with the branch.
<<<
NOTES: >>>
Measured 2026-08-27 on feat/strictdoc-trial at bc646f12, merge base ec980d15.

origin/main carries 0 .sdoc files; the branch carries 9 across three locations.
Every one of the 139 nodes is a first appearance against main today, so the
llm-to-human transition the earlier statement described has no subject yet.
Over the branch's 71 commits: 0 flips and 31 nodes born human, introduced in 13
commits. Creation, not flipping, is what happens.

Why UID-keyed. Commit 4e3f15f4 adds three "+AUTHORED_BY: human" lines: one is a
new node (MECH-PLAN-CHANGE-KINDS) and two are DEC-SYSTEM-PURPOSE and
DEC-PLAN-SINGLE-OWNER relocating from 02-plan-lifecycle.sdoc into
docs/spec/01-plan-model.sdoc. The UID-keyed comparison reports one. Positive
control: the same line scan reports three on 7f6719db, where all three are
genuine new nodes. Thirteen such relocations occurred across the branch.

Why the actor is invisible here. All 71 commits are authored and committed as
the operator and none is signed (%G? = N for all 71), while 31 of the nodes were
written in agent sessions. The 13 commits that introduced them carry no
Co-Authored-By trailer at all; positive control, the same grep finds
"Co-Authored-By: Claude Opus 5 (1M context)" on bc646f12 and 41 such lines
elsewhere on the branch. Commit metadata is not evidence of who acted.

Cost. 0.079 s to compare a 109-node baseline against a 139-node candidate over 9
files (git ls-tree plus one git show per file), 0.063 s against the empty
baseline.

Implementation gotcha. The scan pairs each "UID:" line with the following
"AUTHORED_BY:" line. Both are single-line and field order is enforced, so this
holds under the current grammar and would break silently if the grammar
reordered them. The candidate side can be cross-checked against the JSON export,
which carries AUTHORED_BY for all 139 nodes and agreed exactly with the text
scan (139 nodes, 31 human). The baseline side gets no such cross-check --
exporting a historical tree would require checking it out.

Placement evidence. The flake source store path holds the 9 .sdoc files and no
.git, which is why checks/strictdoc-fp-check.nix and
checks/strictdoc-cycle-check.nix run over ${self} with no history. The precedent
for a history-needing gate in this repo is the gitleaks job at
.github/workflows/ci.yml:718 with fetch-depth: 0. The pre-commit path is gated at
devenv.nix:607 (git-hooks.hooks = lib.optionalAttrs (!isCI)).

Refines SLICE-CHECKPOINT-WIRING, which records this guard as unenforceable until
agents have their own identity. The detection half needs only history and is
enforceable at the CI checkpoint now; only authorization needs the actor.

LEFT TO THE OPERATOR, deliberately. This milestone settles the plumbing;
each of these is a rule about how this instance works and milestone five is
where they get written.

- Whether a reported flip blocks a merge -- promoting the CI job to a required status check is a ruleset change and the operator's alone.

- What an entitled flip by the operator looks like: whether it is accompanied by anything at all, and what form an override takes once MECH-AGENT-IDENTITY-KEYS makes one authenticatable.

- Whether AUTHORED_BY may move human back to llm, and whether an agent rewriting a human-authored statement must make it do so.

- Whether new-human nodes accumulate an acceptance record once reviewed, or are simply re-listed against each pull request's own merge base until they land in main.

- Whether the key means 'the operator wrote these words' or 'the operator originated this node' -- the guard's direction is one-sided either way, but the second reading leaves the words under the key free to drift.
<<<

[MECHANISM]
UID: MECH-SEMBLE-TEST-RECIPE
TITLE: Make a customized semble testable without a devenv shell
DEPTH: sketch
AUTHORED_BY: llm
STATEMENT: >>>
Expose a documented way to build and exercise a grammar-customized semble.
Today it takes a hand-written impure expression against the flake, and the
invocation must scrub PYTHONPATH and redirect the cache.
<<<
RATIONALE: >>>
Measured while verifying SLICE-SDOC-IN-SEMBLE. An installed semble exports
PYTHONPATH, and that shadows any other build: pointing at a freshly built
binary silently runs the installed one with the installed mappings. The failure
presents as the new grammar not working, which is a false defect report waiting
to happen. It already caused one.
<<<

[MECHANISM]
UID: MECH-CHUNK-LEADING-WHITESPACE
TITLE: Chunks can begin on inter-node whitespace instead of the node header
DEPTH: sketch
AUTHORED_BY: human
STATEMENT: >>>
Measured on an 8762-byte document: of 17 AST chunks, roughly five begin on a
blank line between nodes rather than on the node header or field start that
follows. Semble's sibling-merging walk treats whitespace tokens as ordinary
children and folds them into the front of the next group.

Cosmetic. The chunk still covers the right content and search results are
correct; the leading blank lines waste a little of the embedding window and
make a raw chunk read slightly worse.
<<<
RATIONALE: >>>
Logged rather than fixed. Any fix lives upstream in semble's chunker or in a
grammar change that stops emitting whitespace as a sibling, and neither is
worth it for the observed cost. A good candidate to hand to an execution engine
later rather than to spend design attention on now.
<<<

[DECISION]
UID: DEC-FP-FIELDS-CONFIGURABLE
TITLE: Which fields are contract-bearing is configuration, not a constant
AUTHORED_BY: human
STATUS: accepted
RETIRES_ON: >>>
The Nix option surface for custom fields and workflow mechanics exists and the
operator has reviewed the field selection through it.
<<<
STATEMENT: >>>
The set of fields a fingerprint covers is a per-project option, not a hardcoded
list in a script. A prototype may hardcode any reasonable selection to exercise
the logic, but that selection is not settled by having been prototyped.
<<<
RATIONALE: >>>
The selection is the whole mechanism: too broad and every wording change
re-suspects everything until sign-off becomes a rubber stamp, too narrow and a
decision going superseded fails to stale its dependents. That trade is the
operator's to make, and it cannot be reviewed sensibly as an argument in prose
-- it needs the typed option surface the rest of this repository's integrations
are reviewed through.
<<<

[MECHANISM]
UID: MECH-FP-MAIN-LINEAGE
TITLE: Fail safes for fingerprints that reference a state main cannot reconstruct
DEPTH: interface-settled
AUTHORED_BY: human
STATEMENT: >>>
A fingerprint that reaches main names its parent's state in the commit that carries it, so main can always reconstruct that state with git show on the commit and the file. This holds by construction, not by archaeology: an entry naming any other state hashes differently from the tree it lands in, and fp-check already reports that as drifted, or as deleted when the parent is gone.

The fail safe is therefore one gate, not a lineage tracker. fp-check runs against the merge result -- the tree that is about to become main, not a diff against the branch's base -- and refuses the merge when it exits non-zero. Nothing is warned and nothing is re-anchored. Re-anchoring is re-signing, re-signing is an acceptance, and acceptance is the operator's act at pull-request review; a gate that silently re-anchors is the rubber stamp the fingerprint exists to prevent.

Squash needs no special handling. It preserves the final tree, so the signature and the state it names land in the same commit whatever the branch did in between. Rebase and conflict-authored content are a different failure -- the parent's content genuinely changed -- and stay with MECH-FP-GIT-FLOW-HAZARDS.

Reconstruction, meaning answering what changed for a drift already on main, is a diagnostic and is out of scope for this mechanism. If it is built its shape is fixed: walk git log backwards from HEAD over the file holding the parent, export at each candidate commit, hash the parent, stop at the first match. It must hash from the JSON export rather than from the .sdoc text, or it will not reproduce the recorded value.
<<<
RATIONALE: >>>
The two checks this node used to propose were both git archaeology, and the branch they were written for refutes both. origin/main and the merge base ec980d15 each contain zero .sdoc files while HEAD contains nine, so "every recorded hash corresponds to a parent state reachable in main" and "no recorded hash is ahead of the branch's common base" would each refuse all 31 fingerprint entries on this branch. A fail safe that refuses everything on the only live example is not a fail safe, and neither check can run cheaply enough to gate anything.

The replacement costs nothing to build because it is already built. fp-check compares a recorded hash against the parent's hash in whatever tree it is handed and touches git not at all, which is exactly what makes it evaluable against a merge result. What this mechanism adds is not a check but a place to run one.

Storing the accepted parent state beside its hash was considered and rejected. It would make drift diffs answerable without git, and cost is not the objection -- the twelve parents currently referenced total 7.6 KB of contract payload and all 139 nodes total 120 KB. Redundancy is. A state that passes the gate is already in the merge commit, so the store would duplicate the tree to avoid reading it.
<<<
NOTES: >>>
Measured 2026-08-27 against a clean export of the branch tip.

Today the failure has zero instances: fp-check reports 31 fingerprint entries, 0 signed and current, 31 never signed, 0 suspect. Every recorded value is the placeholder 0000000.

Both controls run on copies of the export, never on the tree. Signing MECH-FP-ACCEPT-READINESS against MECH-FP-CHECK's own current hash 5360cbe gives "1 signed and current, 0 suspect", exit 0. The same edge with deadbee gives "drifted -- recorded deadbee, current 5360cbe", exit 1. So the gate fires on a hash naming a state the tree does not contain, and does not fire on one that names the tree itself. fp-check.py:38 lists drifted, unbacked and deleted as failing and returns 1 for any of them; only drifted and deleted are this invariant's cases, unbacked belongs to MECH-FP-RELATION-LINT.

Why reconstruction is a diagnostic and not a gate: a whole-project JSON export takes 2.06 s wall, and there is no cheaper unit -- strictdoc export against a single .sdoc fails with "error: '@repo'" because the grammar alias resolves only from the root strictdoc_config.py. A sweep of this branch's 61 sdoc-touching commits is therefore about 126 s, and after the squash the intermediate states it would search are gone anyway.

PARENT_FP records 7 hex characters (sdoc_fp.HASH_LEN), 28 bits. If a payload store is ever built despite the rejection above, key it by the full digest and resolve the prefix the way git does; 28 bits reaches a birthday collision near 16k stored states.

MECH-FP-PREMERGE-GC should be folded here and retired rather than groomed. Its premise is that fingerprints referencing intermediate branch states become dangling references the instant the branch squashes; under this gate such fingerprints are drifted at the tip and cannot reach main, so there is nothing left to collect. MECH-FP-GIT-FLOW-HAZARDS stays separate: it is about whether a drift report is legitimate, not about whether the state it names survives, and the two overlap only in the sentence "squash is safe", which belongs there.

SLICE-CHECKPOINT-WIRING names its CI checkpoint as "the point where the branch left main". For this invariant that anchor is wrong -- the evaluation tree is the merge result, and a diff against the base cannot see it.

Residual, not handled: a merge that bypasses the gate. Detecting one needs the same fp-check run on main after the fact, which is the same command against a different tree.

LEFT TO THE OPERATOR, deliberately. This milestone settles the plumbing;
each of these is a rule about how this instance works and milestone five is
where they get written.

- Severity of drifted/deleted at every surface other than the merge gate — command time, pre-commit, pre-push. Only the merge boundary is settled here, and only because the consequence there is permanent and no reader judgement is available. The per-checkpoint severity table is SLICE-CHECKPOINT-WIRING's surface and the operator's call.

- Whether the reconstruction diagnostic is built at all. Its shape is fixed above; whether 2.06 s per candidate commit is worth spending, and whether a drift report citing two hashes is already enough, is a judgement about operator attention.

- Who may re-sign after a legitimate drift. DEC-FP-ACCEPT-AUTHORITY is open and this node deliberately does not narrow it — it only rules out the gate re-anchoring on its own.

- Whether main is swept periodically to catch a merge that bypassed the gate. The mechanism is identical (fp-check on a different tree); whether the bypass is worth guarding is a trust question.
<<<
RELATIONS:
- TYPE: Parent
  VALUE: MECH-FP-CHECK
  ROLE: Assumes

[MECHANISM]
UID: MECH-FP-PREMERGE-GC
TITLE: Keep fingerprint lineage during development, collapse it before merge
DEPTH: sketch
AUTHORED_BY: human
STATEMENT: >>>
Permit fingerprints referencing states between the branch head and its common
base with main while the branch is in development, then run a specialized
garbage collection before merge that erases the ones the squash is about to
make unreachable.
<<<
RATIONALE: >>>
Full lineage across a multi-commit pull request is genuinely useful while
working -- it is the trace of how a design was reasoned through. It becomes
dangling references the instant the branch squashes. Collecting at the boundary
keeps the value and pays the cost once.
<<<
NOTES: >>>
Needs grooming, and possibly a plan revision rather than a mechanism: it may
change how MECH-FP-CHECK reports rather than being a separate step. Not settled
that a garbage collection is the right shape.
<<<
RELATIONS:
- TYPE: Parent
  VALUE: MECH-FP-MAIN-LINEAGE
  ROLE: Assumes

[MECHANISM]
UID: MECH-FP-ACCEPT-READINESS
TITLE: Refuse to sign a fingerprint against a parent that is still moving
DEPTH: implemented
AUTHORED_BY: human
STATEMENT: >>>
fp-accept refuses to record a hash for a parent that is not yet stable:
a MECHANISM, SLICE, INVARIANT or SPIKE below interface-settled, or a DECISION
whose STATUS is open.

No new field is needed. DEPTH already distinguishes still-moving from stable,
and STATUS does the same for decisions.
<<<
RATIONALE: >>>
Accepting a contract asserts that no further change is expected. A hash taken
against a node someone is still editing is meaningless: it goes stale the next
day, and the resulting suspect report trains the reader to dismiss suspects.
<<<
PARENT_FP: MECH-FP-CHECK:0000000
NOTES: >>>
Implemented as sdoc_fp.is_ready() (dev/scripts/sdoc_fp.py), the single
readiness predicate dev/scripts/fp-accept.py calls before signing any entry.
Verified against a synthetic fixture covering both refusal branches: a
DECISION with STATUS open and a MECHANISM at DEPTH sketch. Both were
refused with the reason stated; neither was silently skipped.
<<<
RELATIONS:
- TYPE: Parent
  VALUE: MECH-FP-CHECK
  ROLE: Governed_By

[MECHANISM]
UID: MECH-FP-GIT-FLOW-HAZARDS
TITLE: Git operations that change node content before it reaches main
DEPTH: interface-settled
AUTHORED_BY: human
STATEMENT: >>>
Squash-merge is the only method the repository allows, and it is safe for the hash: it preserves the final tree, so a contract hash is byte-identical before and after and matches the branch tip. What it destroys is the ability to reconstruct an intermediate accepted state, and the per-commit attribution of which signature was turned alongside which content change. Under squash-only, and on a branch that restack and absorb routinely rewrite, the durable unit of signature is the pull request, not the commit. MECH-FP-MAIN-LINEAGE and MECH-FP-PREMERGE-GC own that.

The rest of the workflow's hazards, each with what it breaks and who closes it:

- Rebase onto a main whose copy of a parent has moved. The parent's content is genuinely different, so the recorded hash is stale, fp-check reports it drifted and the flake check fails. Detection is correct and already built; what is undesigned is the response, and the response is a signing-authority question, not a git one.
- Conflict resolution inside a parent's contract fields. Produces content neither side authored, and is detected: the parent's hash moves and every child that signed it goes drifted.
- Conflict resolution inside a child's PARENT_FP block. NOT detected. fp-check asserts only that a recorded hash equals the parent's current hash, so any resolution leaving the current hash in place reads as signed and current. This is the same undetectable class MECH-SIGNATURE-REVOCATION measured for a hand-restored line, and it is that node's to close rather than this one's.
- rerere with autoupdate, which is on in this environment. A resolution recorded once is replayed and staged on every later rebase of the same conflict with no prompt, so both conflict hazards above recur through a restack without a human seeing a conflict at all. Restacking is a series of rebases, which is exactly the shape rerere exists to automate.
- Carving the branch into a stack of pull requests. checks/strictdoc-fp-check.nix runs over the whole tree inside nix flake check, a required status check, and fails on any drifted, unbacked or deleted entry. A contract change and every acceptance it invalidates therefore have to land in the SAME pull request: split either way round, the first to merge leaves main red and blocks the rest of the stack, and a pair split so the parent has not landed yet fails as a missing parent instead. This constrains the cut points of SLICE-RESTACK-TO-PRS by the fingerprint graph, not only by readability, and it is the one hazard here that yields a buildable rule rather than a policy question.
- git absorb, git revise and git move routing a hunk into an earlier commit. A PARENT_FP line sits in the same node block as the STATEMENT it signs, so a signature can be absorbed into a commit that predates the state it names. The merged tree is unaffected, so this costs a misleading blame and a possibly red intermediate commit under per-commit testing, not a wrong main.

Out of scope: rebase --update-refs and archive refs move refs, not content; the bot's update/* sweep never touches an sdoc file.

Two questions in this list are the operator's and are deliberately left blank here: whether a rebase should re-accept automatically when the parent's change falls outside the fingerprinted fields, and whether a drifted-on-rebase report blocks or only warns. Both are signing authority, both sit under DEC-FP-ACCEPT-AUTHORITY, and both are settled at the review that defines this instance's semantics.
<<<
RATIONALE: >>>
The enumeration is worth settling now even though the handling stays deferred, because the hazards do not all arm at the same moment and the one that arms first shapes work already scheduled. main carries no sdoc file at all, so nothing on main can move a parent under this branch today; every hazard here arms at the first merge, and the pull-request atomicity constraint arms at the restack that produces that merge. Deferring the whole list until after the first merge would mean discovering the constraint that dictates the cut points while making the cuts.

The handling still waits, and that part of the original deferral holds. What is settled here is which operations are hazards, which are already detected by the checker, and which node owns each one. That is routing, not policy.
<<<
NOTES: >>>
Measured 2026-08-27 in the strictdoc-trial worktree unless stated otherwise.

The fingerprint is a function of file content only. contract_hash hashes the JSON export's node fields, and PARENT_FP is in EXCLUDED_FIELDS beside RATIONALE and NOTES (dev/scripts/sdoc_fp.py:33). That is simultaneously why squash is safe for the hash and why a rewritten PARENT_FP block is invisible to the checker.

rerere.enabled and rerere.autoupdate are both true in file:/home/caubut/.config/git/config -- global, so they apply in every worktree of every clone -- with 35 resolutions already cached in the shared rr-cache. rebase.updateRefs is true there too. 24 worktrees share one common git dir, git-branchless is initialized (.git/branchless exists) and git-absorb is on PATH, so the absorb-routing hazard is a live path rather than a hypothetical.

Nothing has bitten yet, and the reason is measurable: fp-check over the current export reports 31 fingerprint entries, 0 signed and current, 31 never signed, 0 suspect, exit 0. The placeholder never fails the check (fp-check.py:38, FAILING_CASES excludes never-signed), so every hazard here arms with the first real signature -- which per DEC-LONG-LIVED-BRANCH is turned at pull-request review, that is, at the restack.

main holds 0 sdoc files against this branch's 9; the branch is 71 commits ahead of merge base ec980d15.

The gate is real: checks/strictdoc-fp-check.nix is merged into flake.nix's checks (flake.nix:295 and :305), the CI test job runs a plain nix flake check (.github/workflows/ci.yml:591, :643), and test is one of the six required status checks. A missing parent is reported as deleted and fails (fp-check.py:58-60).

Not measured: whether rerere's conflict-hash keying makes cross-node replay likelier in a corpus this uniform, where every node repeats the same field names and similar prose. rerere replays per identical conflict hunk, so two nodes conflicting identically would share one resolution; nobody has produced that case here.

MECH-FP-MAIN-LINEAGE should stay a separate node. It specifies two checks; this one enumerates and routes, and the consumers differ -- SLICE-RESTACK-TO-PRS and MECH-FP-PREMERGE-GC read the enumeration, SLICE-INSTANCE-SEMANTICS-MIGRATION crosses the checks. Merging would give one node that both analyses and specifies. The condition under which merging becomes right is that node's own open question: if merge-time-only signing subsumes both of its checks, it collapses, and its residue is this node's first paragraph.

Correction to what this node used to say. "Costs diagnostics rather than correctness" is right about the hash and understates the attribution loss. DEC-FINGERPRINT-IN-NODE's rationale rests on acceptance being "a reviewable git diff, attributable to a commit"; the commit carrying a signature does not survive squash, restack or absorb. That does not contradict the decision, it fixes the granularity. The earlier NOTES also filed the auto-re-accept question as wanting "a real merge to look at"; it is not a measurement question at all, it is signing authority, and DEC-FP-ACCEPT-AUTHORITY already owns it.

LEFT TO THE OPERATOR, deliberately. This milestone settles the plumbing;
each of these is a rule about how this instance works and milestone five is
where they get written.

- Whether a rebase should re-accept a fingerprint automatically when the parent's change is confined to fields outside the fingerprint. Left blank: it is a signing-authority rule under DEC-FP-ACCEPT-AUTHORITY, which is still open.

- Whether a drifted-on-rebase report blocks the operation or only warns. The mechanism that detects it exists; the severity is policy.

- Whether acceptance is permitted only as the last step before merge. MECH-FP-MAIN-LINEAGE's NOTES treats this as the discipline that might subsume its two checks; it is a rule about when a signature may be turned, so it is the operator's, and whether the checks survive it follows from the answer rather than the other way round.

- Who may re-sign after a conflict resolution, given that the resolver is often the same agent that authored one side. Named but not answered.

- What a revoked-versus-never-signed marker looks like. MECH-SIGNATURE-REVOCATION poses it as a choice between a distinct marker value and a CI history check against main; the PARENT_FP conflict case adds a third caller but does not pick.
<<<
RELATIONS:
- TYPE: Parent
  VALUE: MECH-FP-CHECK
  ROLE: Assumes

[MECHANISM]
UID: MECH-FP-FIELD-TUNING
TITLE: Tune the contract field selection once the option surface exists
DEPTH: sketch
AUTHORED_BY: human
STATEMENT: >>>
Revisit which fields a fingerprint covers, through the Nix option surface,
after the prototype has been in use. The prototype's hardcoded selection is a
starting point chosen to exercise the logic, not a settled answer.
<<<
RATIONALE: >>>
The option surface is not load bearing for building the detector, so waiting on
it would block work for no gain. But the selection does need the operator's
review eventually, and reviewing it as prose was already rejected.
<<<
RELATIONS:
- TYPE: Parent
  VALUE: DEC-FP-FIELDS-CONFIGURABLE
  ROLE: Governed_By

[DECISION]
UID: DEC-FP-ACCEPT-AUTHORITY
TITLE: Who may sign a fingerprint should depend on the grade, not be human-only
AUTHORED_BY: human
STATUS: open
RETIRES_ON: >>>
A real drift event produces enough edges to make the current rule painful,
which is the first evidence of where the line actually belongs.
<<<
STATEMENT: >>>
Human-only signing is the current rule and is too blunt. If a couple of nodes
change in a way that touches a hundred edges without meaning anything, and both
ends are llm-authored and llm-graded, an agent should be able to re-sign those
without raising them.

The line is authority, not effort. A contract the operator authored or accepted
escalates to the operator. One that has only ever been llm-graded does not.
<<<
RATIONALE: >>>
The failure mode of human-only is not that it is unsafe, it is that it floods.
A queue of a hundred no-impact acceptances trains the operator to approve
without reading, which is the same rubber stamp the rule exists to prevent,
arrived at from the other direction.
<<<
NOTES: >>>
Unsettled: whether the deciding field is the PARENT's authority, the CHILD's,
or either end being human. The parent owns the contract that moved; the child
owns the assumption that may no longer hold. Both readings are defensible and
the answer probably wants a real drift event to look at.

AUTHORED_BY already carries the distinction, so this likely needs no new field.
<<<

[MECHANISM]
UID: MECH-RUNTIME-WRITE-GUARD
TITLE: Enforce field ownership at the runtime rather than in a document
DEPTH: interface-settled
AUTHORED_BY: human
STATEMENT: >>>
Two fields are the operator's and the tool never writes them: PARENT_FP and AUTHORED_BY. What enforces that is the absence of a code path, not a check placed in front of one. The sdoc CLI derives its field flags from the grammar it loads, minus a named guarded set, so create and set carry no flag for either field; naming one anyway exits non-zero saying who owns it. There is no override flag, because a flag the model can pass is a document rule wearing a different hat.

The two fields need different handling because the grammar treats them differently. AUTHORED_BY is REQUIRED on all five element types, so create cannot omit it and writes llm unconditionally -- the operator's own authorship is recorded by an edit outside the tool, which stays legal for the operator because the harness denial below binds only agent sessions. PARENT_FP is optional on four types and absent from DECISION, so the tool never emits it at all; dev/scripts/fp-accept.py remains its only writer per DEC-FINGERPRINT-IN-NODE, and this milestone does not absorb that verb into the CLI.

The guarded set is a list of field titles held by the CLI, not an annotation carried on the grammar. That placement is forced rather than preferred: a .sgra file has no syntax for ownership, and the Nix surface that renders docs/sdoc/grammar.sgra is gated on byte identity and model equality with it, so an extra key there fails a check rather than reaching the tool. The list is validated against the loaded grammar, so a guarded name the grammar no longer declares is an error rather than a silently dead entry.

Three things are explicitly out. The harness denial of direct sdoc and grammar edits is SLICE-SDOC-CLI's own clause and stays there: it is a path-based blanket deny of the edit tool, not a field inspection, and a field-inspecting hook on the same paths would be dead code behind it. Ownership as a modelled, general property over arbitrary fields belongs to the semantic layer along with the rest of the special meaning laid over the grammar (MECH-CONTRACT-FIELDS-EDGE-TO-SEMANTIC-LAYER), which is milestone three; this node is deliberately a fixed two-name list so milestone two does not wait on it. State-dependent ownership is out for the same reason -- an accepted DECISION's frozen STATEMENT, and who moves STATUS from open to accepted, which SPIKE-DECISION-ACCEPTANCE-PATH has not yet run on.

What this does not cover, said here rather than left implied: a model that writes a guarded field with a script of its own. Nothing at write time sees that, and no write-time guard reachable in this milestone can. The complete guarantee is detection afterwards -- fp-check for PARENT_FP, already a flake check, and MECH-AUTHORED-BY-GUARD for the other.
<<<
RATIONALE: >>>
Demonstrated rather than hypothetical. A hard rule in the authoring skill did not stop an agent signing five contracts, and because it committed under the operator's name those signatures were forensically indistinguishable from real ones. INV-GUARDS-MUST-EXECUTE records the wider split: every guard that lived in a document failed, every executable one held.

Making the writer incapable of the write is the cheapest executable form and the only one that holds without the harness. Measured: the project settings file that would carry a hook is a devenv shell-entry artifact and is missing from 10 of this clone's 22 worktrees, with no PreToolUse hook at user level behind it. A guard whose guarantee rests on that file is absent about half the time, and absent silently.

An override flag would put the failure back. The incident was a model doing the forbidden thing while holding the document that forbade it; an escape hatch it can reach is the same document with an exit code attached.
<<<
NOTES: >>>
The original statement proposed a tool-call hook and claimed it "works whether the model edits directly or through a script it wrote". The second half is false and was measured on 2026-08-27 against this repository's own guard, packages/claude-code/lib/memory-collision-guard.sh. A PreToolUse envelope carries tool_name and tool_input and nothing else: for Write and Edit that is a file_path, for Bash it is a command string. Positive control, same script, same guarded directory, one run apart -- the Write envelope naming the path returns permissionDecision deny with a populated reason; the Bash envelope whose command writes that same path produces empty stdout and exit 0, which is allow. A Bash matcher can only string-match the command, so it catches an invocation by name and not a heredoc. Logged as MECH-PRETOOLUSE-BLIND-TO-BASH.

Delivery measurement behind the RATIONALE's number: 12 of the 22 worktrees under nix-agentic-tools-worktrees have .claude/settings.json, a symlink into /nix/store written on devenv shell entry and gitignored at .gitignore:38; 10 do not. The user-level ~/.claude/settings.json carries PreCompact and UserPromptSubmit hooks only, so nothing backstops a missing project hook. The same gap currently leaves validate-at-stop unarmed in those 10 worktrees, which is a live finding about this repository rather than a hypothetical about this guard. Logged as MECH-PROJECT-HOOKS-ABSENT-IN-WORKTREES.

Test harness precedent: checks/claude-memory-collision-guard.nix, a hermetic runCommandLocal that drives the script over JSON envelopes, gates it through shellcheck -x, and pins the cadence because a deny that repeats is a livelock. A rejection test for this guard should take that shape, with the positive control being the same verb succeeding on an unguarded field -- otherwise a CLI that rejected everything would pass.

fp-accept.py is guarded by nothing today. Any session can run it and one did. The CLI cannot tell operator from agent either: same binary, same uid, same git identity, which is what MECH-AGENT-IDENTITY-KEYS is about. That is why the discriminator here is the channel rather than the identity -- a harness hook fires only inside an agent session by construction, and the operator running the same command in their own terminal never reaches it.

DEC-FP-ACCEPT-AUTHORITY is open and may later let an agent re-sign contracts that were only ever llm-graded. It does not conflict with this node and is deliberately not a parent: whatever authority rule lands will be implemented by whichever entry point performs the signing, and this node's claim is only that the ordinary authoring verbs are not that entry point. An edge would gate milestone two on an open decision without making the contract any truer.

DEC-EXECUTABLE-RULES-ROADMAP already schedules an operator review of this milestone's verb list before implementation. An objection to create always writing llm belongs at that review, with this statement in front of it.
<<<

[MECHANISM]
UID: MECH-AGENT-IDENTITY-KEYS
TITLE: Give agents their own signing identity
DEPTH: interface-settled
AUTHORED_BY: human
STATEMENT: >>>
An acting identity is a commit-message trailer written by a hook from the environment. It is not a key, not the git author or committer, and not a field on any node.

The trailer names three things the session already knows. Measured in an agent process on 2026-08-27: AI_AGENT=claude-code_2-1-241_agent gives the harness, its version and the role; CLAUDE_CODE_SESSION_ID gives the run; CLAUDE_CODE_CHILD_SESSION=1 marks a subagent, which is the kind of actor that signed the five contracts reverted in 9958f190. A commit-msg-stage hook reads them and appends an Acted-By trailer carrying class, harness and run, so the model never writes it and cannot forget it. commit-msg rather than prepare-commit-msg, because the latter's output is still editable before the commit is made. This repository already installs a prek-managed commit-msg hook for convco, so the wiring point exists.

Absence is a third state. A commit with no trailer is unattributed, not the operator's. The operator's own commits are stamped by the same hook from an environment carrying no agent marker, and that inference is only as strong as whatever launches the session. The prek hooks are local-only and bypassable with --no-verify, so the stamp is evidence, not proof.

A verifier reads git, not the graph: blame the PARENT_FP line in porcelain mode to get the commit, then read that commit's trailer. PARENT_FP entries are UID:hash and carry no signer, and putting one there would store a per-event fact in a per-node field.

No new sdoc field, and AUTHORED_BY is unchanged. AUTHORED_BY is the class of a node's statement author; this is the identity of a single act. A rule keyed on grade reads the first, an audit of who turned a key reads the second. This is also what makes MECH-AUTHORED-BY-GUARD enforceable at a checkpoint rather than only inside the acting session.

Scope is the branch: attribution durable across a branch's own history, which is where the review that catches a bad signature happens. Out of scope, deliberately -- cryptographic signing and key issuance; any rule about who may sign what, which is DEC-FP-ACCEPT-AUTHORITY's; and whether attribution must survive the squash to main.
<<<
RATIONALE: >>>
Per-agent SSH keys were the original shape and buy nothing available here. Nothing on this branch is signed -- 71 of 71 commits report %G? = N -- and the operator's git config declares no gpg.format, no user.signingkey and no commit.gpgsign, so this would be commit signing established from zero. It would not be unforgeable at the end of it: the agent process runs as UNIX user caubut, which owns ~/.ssh/id_ed25519 at mode 0600, so a key the agent can use is a key the agent can substitute. Cryptographic separation needs the operator's key held where the agent cannot reach it, and one machine under one user does not offer that.

The threat is confusion, not forgery. The five signatures were written by an agent that misread its authority, not one that lied about who it was. Attribution answers confusion; only a real principal boundary answers forgery, and there is none to be had here.

The trailer is written by a hook because the convention version has already failed at exactly this. The harness asks the model to add Co-Authored-By, nothing in this repository asks for or checks it, and 41 of the branch's 71 commits carry it while 30 do not -- the 30 including 9958f190 and the rest of the fingerprint incident. A carrier the model writes measured 58% on a branch that is almost entirely model-written.
<<<
NOTES: >>>
Probably belongs to the beads work rather than here, and is likely to get lost there. Tracked in this plan so it survives, not because this is its home.

Measured 2026-08-27 on feat/strictdoc-trial from its fork point ec980d15, 71 commits.

Author and committer are the operator on 71 of 71, so the committer field carries no information today and is available. It is not durable: 41 of 71 commits already have committer-time != author-time, meaning they were re-created and their committer replaced by whoever rebased. Controlled test in a scratch repo -- a commit with committer "claude-code agent" plus an Acted-By trailer keeps both through a fast-forward rebase; git rebase --root --force-rebase resets the committer to the rebaser and leaves the trailer intact. That is why the trailer is the carrier and the committer is not.

Same test, squashed: both gone, and blame on the agent-written line resolves to the operator's single squash commit. Per-line attribution does not survive a squash by construction, whatever the message says, and this repository squash-merges only. MECH-FP-GIT-FLOW-HAZARDS says "Squash is SAFE", which holds for the content hash and is false for attribution.

Positive control for the reader: the same trailer query returned the value on the rebased commit and empty on the squashed one, so an empty result is a real absence rather than a broken query.

Verifier walk-through on the incident line itself -- git blame --porcelain -L85,85 docs/plans/strictdoc-tooling/01-tooling.sdoc gives 9958f190, whose author-mail and committer-mail are both the operator's. The mechanism works and returns the operator for an agent action, which is the defect. git blame prints the author by default; committer appears only under --porcelain, so any check must ask for it.

AI_AGENT is not defined anywhere in this repository -- it comes from the operator's environment. The hook can read it and cannot guarantee it.

LEFT TO THE OPERATOR, deliberately. This milestone settles the plumbing;
each of these is a rule about how this instance works and milestone five is
where they get written.

- Who may sign what, and whether an acting identity grants or withholds authority. This mechanism makes the actor legible and nothing more; DEC-FP-ACCEPT-AUTHORITY is open and unaffected.

- Whether attribution must survive the squash to main, and what carrier could do it. Measured that neither committer nor trailer survives, so the answer is a statement about what the record is for -- and it meets MECH-FP-PREMERGE-GC and MECH-FP-GIT-FLOW-HAZARDS.

- The vocabulary of the actor class. The trailer carries whatever the environment names; whether that vocabulary is AUTHORED_BY's llm/human, a finer grading, or something else is a semantics call, not plumbing.

- Whether an unattributed commit should be refused rather than recorded. The plumbing only distinguishes the three states; turning 'unattributed' into a gate is a rule.

- Whether the operator's own commits should be positively stamped at all, given the stamp is inferred from an absent agent marker rather than asserted.
<<<

[DECISION]
UID: DEC-NO-DELETES-YET
TITLE: Do not delete nodes until the immutability mechanics are settled
AUTHORED_BY: human
STATUS: accepted
RETIRES_ON: >>>
The retention and immutability question settles: whether a node is deleted with
Git history as the record, or is immutable outside explicit state changes.
<<<
STATEMENT: >>>
Supersede, do not delete. Until the record model is chosen, a removed node is
an unrecoverable choice made by whoever happened to be editing.

Known violation, logged rather than reverted: SLICE-SEMBLE-SDOC was deleted
during deduplication, having been written twice in two places. Restoring it
would recreate the duplicate it was removed to fix, so grooming should rule on
whether to reinstate it as superseded or accept the deletion.
<<<
RATIONALE: >>>
The two candidate models -- delete with Git history as the record, versus
immutable outside state changes -- differ in what a deletion costs. Deleting
under the first is routine; under the second it destroys the record. Choosing
by accident, one edit at a time, is how the answer gets made without anyone
deciding it.
<<<

[MECHANISM]
UID: MECH-GROOM-CONTRADICTION-CHECK
TITLE: Grooming must surface contradictions, not just missing edges
DEPTH: sketch
AUTHORED_BY: human
STATEMENT: >>>
When a node is groomed, check whether an edge is missing that should exist, and
whether an existing edge now contradicts what the node says. Surface the
collision rather than silently resolving it.

A live example to test against: DEC-FP-ACCEPT-AUTHORITY holds that human-only
signing is too blunt and should key on grade. At least three places currently
assert human-only outright -- the authoring skill's hard rule, the acceptance
language in DEC-LONG-LIVED-BRANCH, and the two-keys split recorded around
DEPTH verified. None of them cite DEC-FP-ACCEPT-AUTHORITY and none is edged to
it, so nothing connects the open question to the assertions it contradicts.
<<<
RATIONALE: >>>
This is the failure the whole system exists to catch, and it is currently
uncaught in its own graph. The author's stated reason for building this is
returning to a conclusion having forgotten the reasoning; a contradiction with
no edge between its two halves is exactly that, made durable.
<<<

[MECHANISM]
UID: MECH-TESTS-AS-CONTRACT
TITLE: Flows get tests as a contract once they settle
DEPTH: interface-settled
AUTHORED_BY: human
STATEMENT: >>>
Once a flow's mechanics are settled it gets tests that stand as its contract, and no regression is acceptable in this area afterwards. Concretely:

What a test is. A scripted run of one flow through the sdoc tool against a throwaway project, asserting what the flow does rather than what any component says it does. One test is an ordered list of steps; a step names the move, its arguments, and exactly one expected outcome -- writes, giving the field values the move must leave on the node, or refused, naming the identifier of the gate that must have refused it. Assertions are on the gate identifier and on the resulting node fields, never on diagnostic wording. A test that pins prose turns a rewording into breakage, which is this node's own rationale arriving one layer later.

Where it is declared. Beside the flow, in the behaviour model of SLICE-BEHAVIOUR-MODEL, as a tests list on the flow itself. Not as fixture files on disk: a second source for one expectation is the drift MECH-GRAMMAR-GATES-ARE-WRITTEN-TWICE records, and the milestone's premise is that one evaluation emits the model for the tool and the validators both.

Which node type owns it. Neither a new node type nor a new grammar field. A test is data on a flow, so the MECHANISM or SLICE that declares the flow owns it and carries a File relation to the check that runs it.

Where it runs. One generated harness executes every declared flow test and is registered in flake.nix's checks output as strictdoc-flow-contracts, beside strictdoc-fp-check and strictdoc-cycle-check, so nix flake check -- this repository's validation entrypoint -- is what runs it. Each flow gets its own throwaway project and its own --output-dir under the derivation's TMPDIR. No copy in dev/tasks/check.nix: where a working-tree fast path is wanted the task shells out to nix build .#checks.<system>.strictdoc-flow-contracts, which is the one arm of check:sdoc-grammar that already defers instead of restating.

Positive control, per test rather than per suite. A step expecting refused is paired with the same flow run with that gate's precondition removed, which must be accepted. Without the pair, a harness broken in any way at all reports a clean sweep and every refusal in the file means nothing.

The trigger, named in DEPTH. A flow may be built and land at implemented with no contract test. The node that declares it may not move to verified until each of its flows has a test that runs in the check and carries its positive control. That is what "once they settle" means here: implemented is where the mechanics stop moving, verified is the independent pass the ladder already draws, and the requirement needs no new state and no new field.

After a test exists, the flow's declared outcome is the contract. A change to it is read as a contract change, and a test is never relaxed to make a change pass. Whether a flow carrying no test at all fails the evaluation or is only reported in the checkpoint table is SLICE-CHECKPOINT-WIRING's review question, not settled here.
<<<
RATIONALE: >>>
Deliberately after settling, not before. Writing tests against mechanics still being played with pins the wrong thing and makes changing it feel like breakage.

The shape follows from what a flow produces. Its observable product is a sequence of writes and refusals, both exactly reproducible from a fixed starting project, so a fixture run is sufficient; a property test would only re-describe the model that generated the flow, and a golden file over rendered output would assert the renderer. Asserting on gate identifiers rather than on diagnostics buys at the wording level the same freedom that waiting for settling buys at the mechanics level.

Declaring the expectation in the model rather than on disk is this repository's own measured lesson. check:sdoc-grammar and checks/strictdoc-grammar-*.nix implement one acceptance list twice, in bash and in Nix, against the same fixtures; they agree today and nothing makes them agree tomorrow (MECH-GRAMMAR-GATES-ARE-WRITTEN-TWICE).

The per-test positive control is INV-GUARDS-MUST-EXECUTE turned on the tests themselves. Every assertion in a refusal test has the form "this failed", and a broken harness fails everything identically.
<<<
NOTES: >>>
Harness precedent: checks/strictdoc-grammar-negative-fixtures.nix. It builds a throwaway project per fixture outside the repository under TMPDIR, gives each export its own --output-dir, reads each fixture's expected layer out of fixtures/README.md rather than restating it, and carries two positive controls because every assertion in it is of the form "this failed". A flow-contract harness is that file with the fixture table replaced by the model's flow tests. The clean output directory is load-bearing rather than tidy: strictdoc export caches under its output dir, and a broken input exits 1 then 0 on re-run against a warm one.

Corpus, measured 2026-08-27 over the JSON export: 139 nodes; 77 at sketch, 16 at implemented, 2 at verified (SLICE-GRAPH-CHECKS, SLICE-SDOC-IN-SEMBLE). Three File relations exist in the whole graph and all three name implementation files -- packages/semble/lib/withGrammars.nix twice and packages/semble/patches/extra-grammars.patch -- none a check. So scoping the verified requirement to flows is deliberate: no flow exists yet, so the rule is wired against an empty legacy instead of going red on day one, which is the corpus-first order MECH-RELATION-TARGET-TYPE-LINT records. The same rule applied to every node would invalidate both existing verified nodes on the day it landed.

The File edge from a flow's node to its check is documentation, not enforcement. Measured in MECH-FILE-RELATION-EXISTENCE: a File relation whose VALUE names a path that does not exist exports with exit 0. The harness is the enforcement.

The trigger is phrased against the DEPTH ladder as it stands today. If milestone five moves implemented and verified out of DEPTH -- an open instance decision listed in SLICE-INSTANCE-SEMANTICS-MIGRATION -- the trigger moves with them, because the condition it names is the independent review pass rather than the field that carries it.

A flow whose gates read git cannot be exercised the way the existing strictdoc checks are. checks/strictdoc-fp-check.nix and checks/strictdoc-cycle-check.nix run over ${self}, a flake source store path with no .git, and neither dev/scripts/fp-check.py nor dev/scripts/cycle-check.py contains the string git or subprocess (0 matches each; the same grep returns 6 on checks/doubled-words.py and finds subprocess at line 116 of checks/strictdoc-grammar-negative-fixtures.nix, so the search works). SLICE-CHECKPOINT-WIRING's pre-commit checkpoint runs against the previous commit, so any flow reaching it needs a synthetic repository built inside the derivation. Logged as MECH-FLOW-TEST-GIT-CHECKPOINTS rather than solved here.

AUTHORED_BY still reads human. The operator's two sentences are preserved -- the first opens the STATEMENT and the RATIONALE's first paragraph is theirs verbatim -- and everything after them was written by a model. Only the operator turns that key (MECH-AUTHORED-BY-GUARD), so it is left alone and flagged here rather than corrected.

LEFT TO THE OPERATOR, deliberately. This milestone settles the plumbing;
each of these is a rule about how this instance works and milestone five is
where they get written.

- Whether a flow carrying no contract test at all fails the evaluation or is only reported in the checkpoint table. SLICE-CHECKPOINT-WIRING already reserves that same fail-vs-report question for its own review; answering it here would settle a policy in two places.

- Which flows are worth a contract test at all. The mechanism says how a test is declared and where it runs, and deliberately declares no minimum coverage.

- Whether a change to a flow's declared outcome is a signing event. The statement says only that it is read as a contract change; whether it produces a fingerprint, a signature, or a revocation is SLICE-INSTANCE-SEMANTICS-MIGRATION's, and milestone 5's.

- Whether implemented and verified stay in DEPTH at all. The trigger is written against the ladder as it stands and NOTES records that it follows the review pass rather than the field if milestone 5 moves them.
<<<

[MECHANISM]
UID: MECH-READY-QUERY-GRAPH-REUSE
TITLE: MECH-READY-QUERY's closure walk can reuse cycle-check's graph builder
DEPTH: sketch
AUTHORED_BY: llm
STATEMENT: >>>
dev/scripts/cycle-check.py builds a UID -> [(target_uid, role)] adjacency map
over every Parent-type relation via sdoc_fp.build_uid_index and a small
RELATIONS walk. MECH-READY-QUERY needs the same shape of graph to walk a
slice's transitive contract-dependency closure and test each node's DEPTH /
STATUS against readiness. Building it should be factored into sdoc_fp.py (or
a shared graph module) once MECH-READY-QUERY is implemented, rather than
reimplemented.
<<<
RATIONALE: >>>
Noticed while implementing SLICE-GRAPH-CHECKS: MECH-CYCLE-CHECK and
MECH-READY-QUERY both start from "walk the relation graph from a node," and
cycle-check.py already has a tested version of that walk (verified against
synthetic fixtures, see MECH-CYCLE-CHECK's NOTES). Not acted on now --
MECH-READY-QUERY is still needs-design and this is an implementation detail
for whoever designs it, not a reason to touch it while implementing an
unrelated slice.
<<<

[DECISION]
UID: DEC-TUI-BOARD-SUBJECT
TITLE: Whether the board renders plans or work
AUTHORED_BY: llm
STATUS: open
RETIRES_ON: >>>
The TUI's backend is specified against a real data layer rather than fixtures.
<<<
STATEMENT: >>>
The kanban prototype's data model is the earlier overlay's -- TASK, PLAN,
MILESTONE, a work STATUS spanning open through done, and blocking edges. The
grammar in use has none of those: no work-status field anywhere, no milestone,
and node types that describe design rather than work.

A board over the PLAN would reintroduce the work store the plan deliberately
does not keep. A board over the execution engine, fed by the plan at ingest, is
the shape that survives MECH-PLAN-CHANGE-KINDS.
<<<
RATIONALE: >>>
Recorded now because the divergence is invisible while the backend is fixtures
and expensive once it is not. The prototype labels itself honestly -- fixture
backend, no SDoc writes -- so nothing is wrong yet; this is only the fork that
gets chosen when the fixtures are replaced.
<<<
NOTES: >>>
Not a criticism of the prototype, which is deliberately unspecced at this
layer. The operator raised the same gap independently.
<<<

[MECHANISM]
UID: MECH-SDOC-CONFIG-HOOK-IMPORTABILITY
TITLE: strictdoc_config.py must put itself on sys.path before defining a hook class
DEPTH: sketch
AUTHORED_BY: llm
STATEMENT: >>>
On nixpkgs strictdoc 0.27.1, any Format or StrictDocPlugin subclass defined in
strictdoc_config.py crashes every parallelised command -- export with the
default parallelizer, format, manage new, manage auto-uid -- with
ModuleNotFoundError: strictdoc_config in the forkserver workers.
helpers/module.py loads the config by file path without touching sys.path, and
the workers unpickle a ProjectConfig that carries the hook instance. Only
export --no-parallelization survives.

Measured fix: sys.path.insert(0, dirname(abspath(__file__))) as the config's
first statement. All four commands then work, for inline hook classes and for
sibling modules alike. Put the line in the config and in the skill's gotcha
list; drop it once nixpkgs lands >= 0.28.1, whose helpers/module.py does it.
<<<
RATIONALE: >>>
Measured by SPIKE-EXECUTABLE-RULES. Any plugin or Format-seam guard is dead on
arrival without it, and the failure presents as a crash in a worker rather than
as a config error. The upstream fix is the same line moved into the tool, so a
version bump is a convenience here, not a capability.
<<<

[MECHANISM]
UID: MECH-SDOC-LEAN-FORMATS
TITLE: Pin formats to SDoc and JSON in strictdoc_config.py
DEPTH: interface-settled
AUTHORED_BY: llm
STATEMENT: >>>
strictdoc_config.py registers exactly two formats, SDocFormat and JSONFormat,
and there is one config, at the repository root. Not a wrapper-only or CI-only
config: `format` and `manage` take no `--formats` flag, so the project config is
the only lever on their cost, and a second config would be two files obliged to
agree about the same thing.

strictdoc.api exports ProjectConfig and no Format class at all, so the config
imports the two from strictdoc.backend.sdoc.sdoc_format and
strictdoc.backend.json.json_format. That couples the config to non-public module
paths on an overlay that tracks latest upstream, and it fails closed: a renamed
module exits 1 naming strictdoc_config.py and the import line, which the two
corpus-export gates already run.

exclude_doc_paths stays as written. Its two globs cost nothing measurable and
re-arm the moment MarkdownFormat is registered again. What changes is the
docstring, which says both globs are required -- a condition that stops holding.

What the repository gives up is exporting html, html2pdf, rst, markdown, excel,
reqif-sdoc, reqifz-sdoc, doxygen and spdx, and ingesting .md, .markdown and
.gra.md as documents or grammars. Nothing asks for any of them: every check,
script, skill recipe and README line passes --formats=json. .sgra grammar
reading is unaffected -- it comes from SDocFormat, which stays.

What it gains, per invocation on this corpus: export 2.02 s to 1.09 s, format
1.50 s to 0.73 s, manage auto-uid 1.70 s to 0.73 s.

The cost is a false green whose shape is narrower than it looks. Asking for a
handle no registered format claims -- html, rst, markdown, excel, or the bare
default, which is html -- exits 0 and writes no non-cache file. It is confined
to OUTPUT. Validation is unaffected: the traceability index is built before any
format is dispatched, so a corpus with a field-order violation exits 1 under
every one of those handles. Both existing gates read their output file
immediately after exporting and die on its absence, so neither can pass on an
empty export.

Making that loud is owed and is not this node's to build. strictdoc's --formats
allowlist is a hardcoded list of built-in handles that a config can only extend,
never narrow, so the guard belongs in the tool SLICE-SDOC-CLI builds -- the same
slice this mechanism blocks. Until then the mitigation is documentary, which per
INV-GUARDS-MUST-EXECUTE is not a guard and should be written as one that does
not yet execute.

Explicitly out of scope: making HTML render. This node does not repair it, gate
it, or decide whether it should exist -- MECH-DEFAULT-EXPORT-IS-RED-ON-RST is
the instance, MECH-HTML-RENDER-MUST-PASS the requirement. Re-registering
HTMLFormat is that node's change and a one-line revert here.
<<<
RATIONALE: >>>
The traceability index build is 3 ms; the cost of every strictdoc command is
startup, config construction and the format stack default_formats() imports.
This is the single largest lever on the skill loop and on every validation tier,
and it needs no package change.

The fork this node ended on -- pin the formats, or keep HTMLFormat and pay for
it -- collapses on measurement, in both directions.

Keeping HTMLFormat preserves no working HTML export. With HTMLFormat registered,
`strictdoc export . --formats=html` exits 1 on this corpus, aborting partway with
113 files written, because a bare glob in one node's prose is an unterminated RST
emphasis marker. That arm buys a red render for 0.48 s of every command, and the
operator has already ruled the breakage low-priority tech debt that must not
block unrelated work.

Dropping it opens no validation hole. The dangerous reading of the false green --
that the loop the skill documents as "export == validate" would report green on a
broken graph -- is false. Validation happens in the index build, upstream of
format dispatch.

What is left is a real but bounded output trap, in a repository where nothing
invokes an unregistered handle and both gates would fail if one did. Against
roughly halving every strictdoc invocation, on the commands every authoring loop
and both CI checks run, that trades well.
<<<
NOTES: >>>
Re-measured 2026-08-27 against strictdoc 0.28.3, cold cache (clean --output-dir
per run, since the cache lives at <output-dir>/_cache/<version>), on a copy of
the worktree. Interleaved A/B/C rounds, four of them:

  export --formats=json   stock 1.98-2.12 s  lean 1.08-1.13 s  lean+HTML 1.55-1.58 s
  export --no-parallelization --formats=json  stock 2.14-2.28 s  lean 1.31 s (x3)
  format .                stock 1.48-1.97 s  lean 0.70-1.18 s
  manage auto-uid .       stock 1.63-1.78 s  lean 0.71-0.74 s

JSON output is byte-identical across stock, lean and lean+HTML (diff -r over the
json/ tree), and identical again with exclude_doc_paths removed under lean.

FOUR CORRECTIONS to the numbers this node previously carried, all from the
re-measurement above.

The absolute timings do not reproduce. This node said export 3.2 s to 1.24 s;
measured 2.02 s to 1.09 s. The RATIO holds -- pinning roughly halves every
command -- the absolutes do not, so quote the ratio.

The claim that "the forkserver parallelizer adds about 1.4 s" is REFUTED.
--no-parallelization is SLOWER than parallel in both configs, by about 0.15 s
stock and 0.22 s lean. There is no 1.4 s parallelizer tax to recover, and
--no-parallelization is not a lever.

"65 nodes" is stale: the corpus is 139 UIDs across 9 documents.

The fork's second arm was priced at 0.6 s for HTMLFormat; measured 0.48 s
(2.02 vs 1.55). More to the point, what it buys exits 1.

MEASURED, on the false green. Under lean, --formats=html, rst, markdown, excel
and the bare default all exit 0 with zero non-cache files written; the 367 files
in the output dir are all _cache. --formats=json,html writes json/ and exits 0.
Positive control, same binary, same command, HTMLFormat registered: 26 html
files then exit 1 on this corpus, and on a clean two-node mini corpus 5 html
files and exit 0. So "writes nothing" is a property of the format registry, not
of the broken prose.

Second positive control, on the validation half: a field-order violation
injected into 99-backlog.sdoc exits 1 under lean for the bare default, for
--formats=json and for --formats=html alike, with "Semantic error: Wrong field
order". Third: fp-check.py and cycle-check.py both traceback and exit 1 on a
missing index.json, so an empty export cannot pass either gate.

MEASURED, on the markdown half. With MarkdownFormat unregistered, deleting
exclude_doc_paths changes nothing: exit 0, JSON byte-identical, no measurable
time difference (1.06-1.19 s against 1.04-1.20 s). Positive control with the
full format stack and the globs deleted: exit 1, "Reading SDOC: 281 tasks", then
"A process in the process pool was terminated abruptly". That crash is the
reason the globs stay -- they are free, and they are the difference between a
clean export and an unreadable pool failure if MarkdownFormat ever returns.

Upstream mechanics worth not re-deriving. default_formats() (project_config.py
:572) returns 13 Format instances and is used whenever the config passes no
formats= (:411). export_formats defaults to ["html"] (:723), which is why bare
`export` is an html request. ExportAction iterates the REGISTERED formats and
matches them against the requested handles (export_action.py:91), so an
unclaimed handle is a no-op loop -- while needs_html_templates is gated on the
REQUESTED handle (:53), so --formats=html still compiles Jinja templates for
0.53 s before writing nothing. build_index() runs in ExportAction.__init__
(:27), which is why validation is upstream of all of this. EXPORT_FORMATS
(commands/export.py:17) is the hardcoded argparse allowlist and config formats
only append to it (:88), so no config can make --formats=html an argparse error.
DocumentFinder builds its extension table from the registered formats
(document_finder.py:41), which is the whole markdown-ingestion effect.

PROPAGATION, in the same commit. Landing this makes the first sentence of
MECH-DEFAULT-EXPORT-IS-RED-ON-RST false -- bare `strictdoc export .` stops
exiting 1 and starts exiting 0 having written nothing -- so that node's
STATEMENT changes with this one. The config docstring's "BOTH globs are
required" changes too.

A minor lever, measured and not required: importing ProjectConfig from
strictdoc.core.project_config rather than strictdoc.api saves about 0.06 s
(1.06 s against 1.12 s), because strictdoc.api's __init__ imports ExcelGenerator
and so drags openpyxl in even when no Excel format is registered. Under the
stock format list it saves nothing, default_formats() importing the same modules
a moment later.
<<<

[MECHANISM]
UID: MECH-READINESS-PREDICATE-RECONCILE
TITLE: One readiness predicate, consumed by every script that asks
DEPTH: interface-settled
AUTHORED_BY: llm
STATEMENT: >>>
Readiness is defined in four places, read at two scopes, and the four disagree. dev/scripts/sdoc_fp.py:100 is_ready is the node-local rule fp-accept consults before signing a fingerprint. docs/sdoc/status.py:58 closure_verdict re-implements the same rule inline while walking a slice's closure. dev/skills/sdoc/SKILL.md:68 and MECH-READY-QUERY state it in prose, identically to each other and differently from both executables. DEC-LOCAL-IMPLEMENTABILITY is the contract all four claim to implement and enumerates no state at all.

Measured disagreement, four cells. A rejected decision: both executables pass it, both prose readings block it. A superseded decision: fp-accept signs against it, status.py blocks. A SPIKE whose STATUS is unrun or blocked: every reading treats it as settled on DEPTH alone, because no gate consults a spike's STATUS. A suspect edge: DEC-LOCAL-IMPLEMENTABILITY makes it part of the predicate, and status.py never computes one because it never calls fp-check.

The dependency edge set is defined twice with complementary filters -- status.py:47 takes every relation whose TYPE is not File, sdoc_fp.py:97 takes every relation whose TYPE is Parent -- and the DEPTH ladder is written three times in two languages: packages/strictdoc-grammar/values.nix:35, status.py:33, sdoc_fp.py:38.

The deliverable is one read point, not a ruling. The predicate and the edge-set live in dev/scripts/sdoc_fp.py, which cycle-check.py already imports by the sys.path.insert idiom the dev/scripts carry; status.py and render.py gain that import rather than moving, because checks/strictdoc-fp-check.nix and checks/strictdoc-cycle-check.nix name dev/scripts/ paths while the skill names docs/sdoc/ paths. It exports four things, and nothing outside it decides readiness:

STATE_VERDICTS -- a table from one state-field value to settled, blocks or freedom. Seven rows: one per DECISION STATUS, one per SPIKE STATUS, plus the cut point on the DEPTH ladder. Its contents are milestone 5's, listed below.

settled(node) -> (bool, reason) -- the node-local question fp-accept asks of a single parent, answered from the table.

dependencies(node) -> set of UID -- the one edge-set: every relation whose TYPE is Parent, plus every PARENT_FP parent. TYPE is Parent, not "is not File": a Child relation points downstream and is not a dependency, and status.py's complement filter would walk one into the closure the day the grammar declares one.

suspect_edges(index) -> set of (node, parent) -- fp-check.py:42's drifted, unbacked and deleted findings lifted out so a closure walk can apply the no-suspect-edge condition status.py omits. never-signed is not suspect.

After the change fp-accept calls settled, fp-check calls suspect_edges, status.py's closure_verdict calls all four and holds no rule of its own, and MECH-READY-QUERY calls the same four when it lands. cycle-check.py's build_graph moves here too. It filters TYPE == Parent, which is the SAME edge set and the same direction as sdoc_fp.relation_parent_uids and differs only by carrying the ROLE alongside the target, so it takes a flag for whether the role travels and another for whether PARENT_FP parents count as edges. render.py computes no readiness and only imports the fingerprint placeholder.

Behaviour is held constant except where a gate tightens. The shipped table transcribes status.py's current reading, the stricter of the two executables on the one cell where they differ, so fp-accept stops signing against a superseded parent and no other output moves. Transcribing rather than ruling is the point: which states are settled is not this mechanism's to decide.

Left blank for milestone 5, one cell each: whether rejected blocks; whether superseded blocks; whether a decision that is neither open nor accepted contributes a degree of freedom; whether a SPIKE's STATUS gates at all and which of unrun and blocked blocks; and whether no-suspect-edge belongs in the predicate or in a separate report. When SLICE-BEHAVIOUR-MODEL's evaluation emits its machine-readable model, the table becomes a projection of it and stops being a literal.

Done when all five scripts produce byte-identical output on the current corpus, except fp-accept's superseded refusal, and the injected-state control below is re-run against the module.
<<<
RATIONALE: Two executables carrying two readings of one rule is the document-borne drift INV-GUARDS-MUST-EXECUTE names, and the rule is the one part of this that should not be code: it is lifecycle policy, which DEC-EXECUTABLE-RULES-ROADMAP puts in milestone 5. Separating the read point from the rule now means milestone 5 fills a seven-cell table instead of editing four scripts in two directories, and means the disagreement is inspectable as data rather than distributed across two hand-copied constants and two inline conditionals. Deferring the extraction until milestone 5 inverts that: the migration would arrive to find the thing it migrates written four times.
NOTES: >>>
Measured 2026-08-27 against a clean export of 139 nodes (rm -rf of the output dir first; incremental export produces false greens). Relation TYPE census: Parent 92, File 3, Child 0. DECISION STATUS: 13 accepted, 7 open, 1 superseded, 0 rejected. DEPTH: 77 sketch, 16 implemented, 14 interface-settled, 9 needs-design, 2 verified, 21 decisions carrying none. Fingerprints: 31 entries, 31 never-signed, 0 suspect -- so no-suspect-edge is vacuously true today and starts to matter at the first signed fingerprint.

How much of the divergence is latent, and how much is not. Latent: zero rejected decisions exist, and the one superseded decision, DEC-VIEWER-BEFORE-BULK, has zero inbound relations and is named by zero PARENT_FP entries. Not latent: SPIKE-CONVERSION-SIGNAL is STATUS unrun at DEPTH interface-settled, so both predicates already count an unrun spike as settled wherever it appears in a closure. Also not yet live but one grammar edit away: packages/strictdoc-grammar/lib/dsl.nix:123 already offers rel.child, and values.nix:8 records the child relation as surface this repository does not exercise.

Positive control, run in memory over a deep copy of the export with no file written. Setting DEC-ARCH-COLOCATION's STATUS to each of the four values in turn: open -> fp-accept refuses and status.py blocks; accepted -> fp-accept signs and status.py passes; rejected -> fp-accept signs and status.py passes; superseded -> fp-accept signs and status.py blocks. The control detects agreement as well as disagreement, so the one divergent row is not an artefact of the harness. Setting SPIKE-EXECUTABLE-RULES's STATUS to unrun, run and blocked in turn changes neither answer. Appending one TYPE Child relation to MECH-CYCLE-CHECK makes status.py's dependencies return two UIDs where sdoc_fp's relation_parent_uids returns one.

Three implementations of node discovery also exist -- the recursive UID-prefix walk in status.py:20, the same walk in render.py:27, and the DOCUMENTS/NODES walk keyed on _NODE_TYPE in sdoc_fp.py:45 -- and all three return the same 139 nodes today. They are out of scope here and logged separately; the count is recorded so a later divergence is legible as a change rather than a discovery.

Sequencing. MECH-READY-QUERY and this node are not the same work and do not merge: this one produces the predicate and the edge-set, that one the closure query and the bounded implementation prompt built from the same traversal. MECH-READINESS-REPORT-FRONTIER is a different case -- both of its complaints, a root reporting itself as its own blocker and an undifferentiated blocker list, are answered by MECH-READY-QUERY's record, so it closes as subsumed when that lands. This one lands first and changes no output; the other two consume it. MECH-READY-QUERY carries only a Governed_By edge to DEC-LOCAL-IMPLEMENTABILITY and has no edge recording that dependency.

Correction to this node's earlier statement, kept so the change is legible. It said five definitions exist and no two agree. There are four readings, not five -- DEC-LOCAL-IMPLEMENTABILITY is the contract the other four implement, not a fifth reading of it -- and two pairs do agree: the skill and MECH-READY-QUERY word it identically, and on rejected the two executables agree by both passing it. The executables differ in exactly one cell, superseded. It also cited SLICE-SDOC-IN-SEMBLE being verified while status.py reports it blocked on DEC-ARCH-COLOCATION; that reproduces exactly, but both predicates answer the same there, so it is DEPTH and closure-readiness being independent axes rather than two predicates disagreeing, and it is already recorded verbatim in MECH-READY-QUERY's own notes.

LEFT TO THE OPERATOR, deliberately. This milestone settles the plumbing;
each of these is a rule about how this instance works and milestone five is
where they get written.

- Whether a `rejected` decision in a closure blocks. Both executables currently pass it; both prose readings block it. Zero instances exist today.

- Whether a `superseded` decision blocks. This is the single cell where the two executables actually disagree today. The one superseded decision has no dependents.

- Whether a decision that is neither open nor accepted contributes to the degrees-of-freedom count, or only to the blocker list.

- Whether a SPIKE's STATUS gates at all, and if so which of `unrun` and `blocked` blocks. DEPTH describes a spike's design maturity and STATUS its execution; nothing today says whether an unrun spike may sit in a settled closure.

- Whether no-suspect-edge is part of the readiness predicate, as DEC-LOCAL-IMPLEMENTABILITY words it, or a separate report status.py prints alongside its verdict.

- Whether the DEPTH cut point stays at interface-settled for every node type, or differs per type.

- The shipped table transcribes status.py's reading as a placeholder so no gate loosens. That transcription is not a ruling on any cell above and is expected to be replaced wholesale at milestone 5.
<<<
RELATIONS:
- TYPE: Parent
  VALUE: DEC-LOCAL-IMPLEMENTABILITY
  ROLE: Governed_By

[MECHANISM]
UID: MECH-RELATION-TARGET-TYPE-LINT
TITLE: Lint relation target types, which the parser never checks
DEPTH: interface-settled
AUTHORED_BY: llm
STATEMENT: >>>
A relation's legal target type is a contract keyed on the pair (source element tag, relation role), not on the role alone. The grammar declares thirteen Parent relations across the five element types, so the table has thirteen rows, one per declared pair. File relations carry no row: their VALUE names a filesystem path, not a UID.

| source | role | legal target |
| --- | --- | --- |
| DECISION | Superseded_By | DECISION |
| MECHANISM | Governed_By | DECISION |
| MECHANISM | Guarantees | INVARIANT |
| MECHANISM | Serialized_By | (none yet) |
| MECHANISM | Proven_By | SPIKE |
| MECHANISM | Assumes | DECISION, MECHANISM |
| SLICE | Governed_By | DECISION |
| SLICE | Crosses | MECHANISM |
| SLICE | Assumes | DECISION, SLICE |
| SLICE | Proven_By | SPIKE |
| INVARIANT | Governed_By | DECISION |
| INVARIANT | Proven_By | SPIKE |
| SPIKE | Governed_By | DECISION |

Two absences are represented differently and both are load-bearing. A pair the grammar declares with no row at all is an evaluation error, so a role cannot exist without a contract. A row whose target set is empty, carrying a reason, means the role is grammatically available and deliberately has no contract yet; every use of it is a violation reporting that reason rather than passing. Serialized_By is the only such row, because nothing uses it and MECH-CORPUS-EDGE-MAP defers it until the locks document converts.

The table lives in the milestone-three behaviour-model surface, layered over the normalized grammar surface rather than inside it. SLICE-GRAMMAR-FROM-NIX excludes "which node types a relation may point at" by name and assigns it to a consumer of that surface. The join key is the element tag and the relation role, both already carried by the normalized layer.

Three checks run at evaluation, against the grammar values in the same evaluation: every declared (element, role) pair has exactly one row, every row names a pair the grammar declares, and every target names a declared element tag. A role renamed or dropped upstream therefore fails evaluation instead of leaving a row that silently covers nothing.

One check runs over the corpus: dev/scripts/relation-target-check.py, taking a clean JSON export and the machine-readable model emitted by that same evaluation, so the table exists once and no second copy can drift. It walks every Parent-type relation, resolves both ends to their _NODE_TYPE, and reports each edge whose target tag is outside its row's set, printing source UID, role, target UID, the target's actual tag and the legal set. Exit status is non-zero when any violation is found, and the summary line is "N nodes, M parent edges checked: K violation(s)" -- MECH-CYCLE-CHECK's shape, for the same reason: a count is what makes a green run distinguishable from a run that checked nothing. Its CI gate is checks/strictdoc-relation-target-check.nix, mirroring checks/strictdoc-cycle-check.nix's clean-$TMPDIR export harness rather than sharing its derivation, so the two stay independently attributable on failure. Dangling targets need no handling: a VALUE naming no node is already fatal at parse.

There is no exemption or allowlist mechanism. The corpus is fixed before the gate lands, and that is two edges:

SPIKE-CONVERSION-SIGNAL Governed_By SLICE-FIRST-CONVERSION becomes SLICE-FIRST-CONVERSION Proven_By SPIKE-CONVERSION-SIGNAL. SPIKE declares only Governed_By and File, so a spike has no role that can name what it probes; the reverse direction is expressible and is how the other seven spike citations are already written.

MECH-FP-ACCEPT-READINESS Governed_By MECH-FP-CHECK becomes Assumes. It refines fp-check's behaviour rather than being governed by a decision, which is what the seven other MECHANISM-to-MECHANISM edges say. Its PARENT_FP entry stays and needs no re-signature: RELATIONS is excluded from the contract hash, so changing a role does not move it.

The thirteen rows are data filling this surface, not part of it. Turning a row is a one-line edit that does not touch this mechanism.

Refusing the write at edit time belongs to milestone four, in the sdoc CLI, consuming the same emitted model. It is not part of this mechanism.
<<<
RATIONALE: >>>
The parser proves an edge resolves, never that it points at the kind of node the role promises. Measured on a scratch copy of the corpus: a SLICE Crosses a DECISION, and a DECISION Superseded_By a MECHANISM, both export with exit 0 and the edge intact in the JSON. The second is the worse of the two, because the skill's supersession rule is the one place the graph claims a discipline no mechanism enforces.

Key the contract on the pair rather than on the role because the corpus already uses one role from several source types with different targets. Assumes is MECHANISM-to-MECHANISM seven times and SLICE-to-SLICE six; a role-keyed table would have to admit the union and would then permit MECHANISM Assumes SLICE, which nothing has argued for. Governed_By is declared on four of the five element types.

Corpus first, gate second is this repo's own practice from SLICE-FP-DETECTOR. A lint wired before the two miscast edges are fixed is red on day one, and a check that is red on arrival is a check people learn to skip.

The table belongs to the semantic layer rather than the grammar surface because that is where the operator can see it. Milestone three exists so the lifecycle becomes something to look at instead of guess at, and a target-type table hidden in a Python dict is prose again.
<<<
NOTES: >>>
MEASURED 2026-08-27, strictdoc 0.28.3 via the trial venv, against a byte-copy of the corpus in a scratch tree (139 nodes, identical to the live export). Every injection went into the same file at the same anchor and each ran against its own clean output directory.

Silent: SLICE-GRAPH-CHECKS --Crosses--> DEC-SYSTEM-PURPOSE exits 0, and the edge is present in the export's RELATIONS. DEC-VIEWER-BEFORE-BULK --Superseded_By--> MECH-CYCLE-CHECK exits 0 with zero error lines.

Positive controls, same harness, same file, same anchor -- what strictdoc does check, so the two exit-0 results above are a real absence and not a broken injection. A role the source element does not declare (SLICE ... ROLE: Guarantees) exits 1 with "Semantic error: Requirement relation type/role is not registered: Parent / Guarantees". A target UID that does not exist exits 1 with "[DocumentIndex.create] Requirement SLICE-GRAPH-CHECKS references parent requirement which doesn't exist".

A thirteen-row prototype of the checker over the live export: 139 nodes, 92 parent edges checked, 2 violations -- exactly the two named in the STATEMENT. Re-run against each injected export it reported 3, catching the injected edge alongside them.

THE ROLE TABLE HAS TWO AUTHORITIES AND THEY DISAGREE. MECH-CORPUS-EDGE-MAP is interface-settled, fingerprinted, and states a role table of its own: Assumes MECHANISM-to-DECISION, Proven_By MECHANISM-or-INVARIANT-to-SPIKE, Governed_By MECHANISM-to-DECISION. The live graph matches none of those three. It has zero MECHANISM Assumes DECISION edges against seven MECHANISM-to-MECHANISM and six SLICE-to-SLICE; zero MECHANISM or INVARIANT Proven_By against seven SLICE-to-SPIKE; and Governed_By sourced from SLICE, INVARIANT and SPIKE as well as MECHANISM. The rows above are the union, on the reading that MECH-CORPUS-EDGE-MAP forecasts how one unconverted corpus will be converted (its counts are of source material, not of nodes that exist) while this table is graph-wide. The union is safe because the argument that motivated its narrower Assumes -- "any-to-any is a cycle generator", written when nothing detected cycles -- has since been discharged by MECH-CYCLE-CHECK, which is implemented and gated in CI. Its STATEMENT is a contract field, so reconciling it is the operator's: MECH-EDGE-MAP-TABLE-RECONCILE.

Logged, not decided: no Assumes edge in the graph carries a fingerprint, 0 of 14, while Governed_By carries one on 17 of 26 and Crosses on 3 of 29. The skill's fingerprint ladder runs strictly downward, DECISION to MECHANISM to SLICE, and has no place for a same-tier Assumes. Whether such an edge is contract-bearing at all is DEC-ASSUMES-CONTRACT-BEARING.

Grammar counts, for the evaluation cross-check to assert against: thirteen Parent (element, role) pairs and three File relations, from packages/strictdoc-grammar/values.nix. That file is the consumer holding this repository's five node types; the table sits beside it as a second consumer of the same surface, not inside it.

CORRECTIONS TO THIS NODE'S EARLIER STATEMENT, all from graph growth between 61 and 139 nodes. It said five MECHANISM Assumes MECHANISM edges; there are seven. It said the skill's table gives Assumes no target and Serialized_By none at all -- true of the skill, false of the graph, since MECH-CORPUS-EDGE-MAP gives both a stated home and defers Serialized_By explicitly. And it scoped the gap to Governed_By, Assumes and Serialized_By; measured, no role is checked, Superseded_By included.

LEFT TO THE OPERATOR, deliberately. This milestone settles the plumbing;
each of these is a rule about how this instance works and milestone five is
where they get written.

- The thirteen row VALUES are a proposal derived from measured usage plus the skill's prose table. They are data filling the surface; the operator turns any row without touching this mechanism

- MECHANISM Serialized_By is deliberately left with an EMPTY target set rather than a guessed one. Nothing uses the role and MECH-CORPUS-EDGE-MAP defers it; the first person who wants it writes its contract

- Whether an Assumes edge is contract-bearing at all — 0 of 14 carry a fingerprint, and the skill's downward ladder has no place for a same-tier edge. Left to DEC-ASSUMES-CONTRACT-BEARING and to milestone 5's ripple model

- Whether per-plan narrowing of the table (a profile, so the beads corpus could enforce a tighter Assumes than the graph-wide contract) should exist. The union is proposed instead; the narrowing question is logged, not answered

- Reconciling MECH-CORPUS-EDGE-MAP's STATEMENT with the graph-wide table. It is a contract field on a fingerprinted node, so only the operator changes it
<<<
RELATIONS:
- TYPE: Parent
  VALUE: MECH-CYCLE-CHECK
  ROLE: Assumes

[MECHANISM]
UID: MECH-PLAN-REFS-CHECK
TITLE: Check INV-NO-EXTERNAL-PLAN-REFS over the export
DEPTH: interface-settled
AUTHORED_BY: llm
STATEMENT: >>>
A node is in plan P when its source file is under docs/plans/<P>/. Everywhere else is outside every plan: docs/spec/, **/.sdoc/, and any location added later. The check reports a Parent-type relation whose target is in a plan and whose source is not in that same plan. Another plan counts as outside -- both live violations are plan-to-plan, not architecture-to-plan.

File relations are excluded, as in cycle-check.py and fp-check.py: their VALUE names a filesystem path, not a node. PARENT_FP entries are scanned as a second case, since an entry unbacked by a relation has no edge for the first pass to see.

The export carries no source path for a node, so the check takes a repository root alongside the export and builds a UID-to-file map by scanning docs/**/*.sdoc and **/.sdoc/*.sdoc for a line-anchored ^UID: (\S+)$. A UID present in the export that the map cannot place is a finding, not a skip: treating an unplaceable node as outside would pass silently, which is the false-green shape the other graph checks exist to avoid. The map builder lives in dev/scripts/sdoc_fp.py beside the other shared logic, and fp-accept.py's own discovery is replaced by it.

The CLI is dev/scripts/plan-refs-check.py <export.json> --repo-root PATH. It groups findings by case under a `== case (n) ==` header, prints a one-line summary of what was checked whether or not anything failed, and exits non-zero on any finding -- the shape cycle-check.py and fp-check.py already use. A check(index, uid_file) function returns the findings without printing, so SLICE-CHECKPOINT-WIRING can register it as a validator rather than shell out to the CLI.

The gate is a flake check, checks/strictdoc-plan-refs-check.nix, registered in flake.nix's checks output: its own runCommand with its own clean $TMPDIR export, mirroring checks/strictdoc-cycle-check.nix rather than sharing a derivation, so a failure stays attributable to this check. No devenv task. MECH-CHECK-SYSTEM-BOUNDARY's position is that the flake output is the gate and a devenv task should defer to it rather than restate it; neither sibling graph check has one, and the interactive path is the strictdoc CLI devenv.nix already ships.

Corpus before gate, as with SLICE-FP-DETECTOR: the two violating Assumes edges are deleted and the dependency restated as prose in the depending node's NOTES, in the same commit that wires the check, so the gate does not land red.
<<<
RATIONALE: >>>
Predicted by the invariant's own NOTES and now measured. The check itself is a few dozen lines over data the export already holds; what needed settling was the definition of outside a plan, and where the source-path information comes from, since the export has none.

Defining plan membership positively -- docs/plans/<P>/ and nothing else -- rather than enumerating what counts as outside is what makes the rule survive a new location. docs/spec/ already exists and is absent from the sdoc skill's layout table; an enumerated complement would have silently exempted it.

Deleting the two edges rather than waiting for their targets to graduate is the unblocked move. Both are Assumes, neither carries a fingerprint, so nothing is being un-signed. The better fix -- promoting MECH-FP-CHECK and MECH-CYCLE-CHECK out of the plan into settled specification, which would make both edges legal outward references -- needs a promotion path, and that waits on DEC-PLAN-LIFECYCLE-OPEN.
<<<
NOTES: >>>
Measured at bc646f12 against a clean export of the whole repository: 139 nodes, 92 Parent-type edges, 2 violations. MECH-RENDER-CACHE (docs/plans/beads-migration/00-approach.sdoc) --Assumes--> MECH-FP-CHECK, and MECH-CORPUS-EDGE-MAP (docs/plans/beads-migration/02-conversion-map.sdoc) --Assumes--> MECH-CYCLE-CHECK, both landing in docs/plans/strictdoc-tooling/01-tooling.sdoc. No PARENT_FP entry crosses a plan boundary today.

The inbound arm the invariant is actually named for -- settled architecture depending into a plan -- has zero live hits, so it was proven with a positive control rather than assumed. Injecting MECH-SEMBLE-EXTRA-GRAMMARS --Assumes--> MECH-FP-CHECK into a copy of the export takes the count from 2 to 3 and reports the new one as inbound. Two negative controls hold the count at 2: an outward edge from a plan node to INV-GUARDS-MUST-EXECUTE in docs/spec/, and a File relation whose VALUE is a path under docs/plans/. A third positive control removes MECH-FP-CHECK from the map, and the check reports it unmapped rather than passing.

The export carries no document path. Walking every key at every depth of the 393 KB index.json yields no key containing PATH or FILE; the only paths present are File-relation VALUEs. docs/sdoc/render.py reads RELATIVE_PATH or PATH per node, and neither is ever there.

fp-accept.py's map is wrong twice and must not be copied. Its find_source_file substring-matches `UID: <uid>`, so a UID that is a prefix of another resolves to whichever file rglob reaches first: measured, MECH-READY-QUERY resolves to 99-backlog.sdoc, where MECH-READY-QUERY-GRAPH-REUSE lives, while the node itself is in 01-tooling.sdoc; MECH-STRICTDOC-DEVENV-MODULE has the same shape against MECH-STRICTDOC-DEVENV-MODULE-NOT-PUBLISHED. And its discover_sdoc_files scans docs/plans and **/.sdoc only, so the four nodes in docs/spec/01-plan-model.sdoc are invisible to it. The line-anchored scan places all 139.

Cost: 9 ms to build the map over the whole worktree, 0.1 ms to run the check. The strictdoc export dominates, and this makes a fourth export of the same corpus inside nix flake check.

The source-annotation arm is unenforceable with this input. The invariant names source annotations, but strictdoc_config.py sets no source root, no annotated node exists, and @relation comments never appear in the JSON export. This check covers document-to-document edges only; the annotation arm needs a different input and is out of scope here.

LEFT TO THE OPERATOR, deliberately. This milestone settles the plumbing;
each of these is a rule about how this instance works and milestone five is
where they get written.

- Whether a plan-boundary violation FAILS a checkpoint or only REPORTS at it. This node fixes the CLI's own exit code to non-zero, matching cycle-check.py and fp-check.py, because that is the flake-check contract. How the same validator behaves once SLICE-CHECKPOINT-WIRING registers it at command, commit and merge time is that slice's review question, not settled here.

- The retention and promotion policy that would make the two live edges legal instead of deleted -- promoting an implemented mechanism out of a plan into settled specification. That is DEC-PLAN-LIFECYCLE-OPEN, still open, and its RETIRES_ON has not been met.

- Whether the invariant's source-annotation arm is ever enforced, and against what input. Recorded as out of scope with a reason, not decided.
<<<
RELATIONS:
- TYPE: Parent
  VALUE: INV-NO-EXTERNAL-PLAN-REFS
  ROLE: Guarantees

[MECHANISM]
UID: MECH-SIGNATURE-REVOCATION
TITLE: Make a revoked fingerprint distinguishable from one never signed
DEPTH: interface-settled
AUTHORED_BY: llm
STATEMENT: >>>
A PARENT_FP entry's value slot carries three states rather than two: the placeholder 0000000, meaning nobody has accepted this edge; a seven-character contract hash, meaning the edge was accepted at that hash; and revoked:<hash>, meaning an acceptance at that hash was withdrawn. The tag cannot be mistaken for a hash, since hashes are hexadecimal and the tag is not, and the existing parser already returns the value slot whole. Carrying it therefore needs no grammar change -- PARENT_FP is an unconstrained String -- and no parser change.

fp-check gains a fifth case beside never-signed, drifted, unbacked and deleted. It is tested after unbacked and before the drift comparison; in the other order a revoked entry is reported as drift. The report names both the withdrawn hash and the parent's current hash, because equality between the two is the restoration risk: the contract has not moved since it was revoked, so a hash copied out of the reverting commit still reads as current. Revoked ships in the same non-failing bucket as never-signed, so a revocation never turns the gate red. Which cases fail is one named set in the checker, and setting it is the operator's rule, not this mechanism's.

Writing stays with the single writer that owns PARENT_FP today, as a revoke verb on it rather than a second tool and never as a hand edit -- fp-accept now, the sdoc CLI's verb list when that lands, a move in the behaviour model after that. Two refusals are what give the marker meaning. Revoking an entry still at the placeholder is refused, because there is nothing to withdraw. Signing over a revoked entry is refused, so re-signing becomes a deliberate request to clear a revocation instead of something a re-run does silently. Who may make that request is DEC-FP-ACCEPT-AUTHORITY's to answer.

The on-disk record is deliberately the minimum: the tag, the withdrawn hash, one state per edge, no history. Who revoked, when and why live in the commit, which is where DEC-FINGERPRINT-IN-NODE already puts the sign-off. An entry additionally carrying an actor, a timestamp or a reason would be per-edge state a node field cannot hold, which is that decision's own retirement condition.

Detecting a hand-restored signature is out of scope and cannot be done from the file, because whoever restores it controls the file. That needs history against main (MECH-FP-MAIN-LINEAGE) or an identity the commit is attributable to (MECH-AGENT-IDENTITY-KEYS), both deferred. What this mechanism buys is that a restoration becomes the visible deletion of a named marker rather than an invisible edit of seven zeros.
<<<
RATIONALE: >>>
The revert in 387cdaec was the right call and left no trace the checker can see. A signature that can be silently restored is the rubber stamp the mechanism exists to prevent, arrived at through git.

The sketch offered a history check in CI against main as the alternative. It does not fit the gate that exists: checks/strictdoc-fp-check.nix runs over the flake source, and a flake source copy carries no .git, so a history check would have to be a second, git-aware gate outside nix flake check. The marker also works in a worktree before anything has reached main, which is where every acceptance in this plan will be taken. History stays the only way to catch a restoration performed by hand, so the two are complements rather than alternatives, and the marker is the half that is buildable now.

Keeping the record inside PARENT_FP rather than in a sidecar is the same argument DEC-FINGERPRINT-IN-NODE made for the fingerprint itself: the state transition is a reviewable diff hunk, attributable to a commit and revertable.
<<<
NOTES: >>>
Measured 2026-08-27 against the JSON export, using fixtures in a scratch copy; the worktree was not touched.

Baseline: 31 fingerprint entries, 0 signed and current, 31 never signed, 0 suspect.

The four distinct hashes 387cdaec reverted -- b2c00b4, ff63967, 5360cbe, 704b6d9 -- are all still the current contract hashes of their parents. Writing b2c00b4 back into MECH-FP-CHECK's entry gives "1 signed and current, 0 suspect" and exit 0: a restoration copy-pasted out of the revert diff is accepted with no complaint. Positive control on the same fixture: deadbee in the same slot gives "1 suspect" and exit 1, so the harness does detect a bad hash.

Third fixture, DEC-FINGERPRINT-IN-NODE:revoked:b2c00b4 against today's checker: classified drifted, exit 1. The marker is therefore not inert -- shipping the representation without the classification turns all five reverted entries into false suspects. With the classification, the honest state of this graph is 26 never signed and 5 revoked out of 31.

parse_parent_fp partitions on the first colon, so the value slot already survives whole: the fixture parses to ('DEC-FINGERPRINT-IN-NODE', 'revoked:b2c00b4'). Longest possible rendered entry across this graph is 50 characters, MECH-READINESS-PREDICATE-RECONCILE:revoked:0000000, or 61 with the single-entry field prefix, so no line-width question arises.

The flake source store path contains docs/plans and no .git, which is what rules the history check out of the existing gate.

Whether strictdoc format normalises a PARENT_FP block was not re-measured and no longer matters: distinguishability lives in the value slot, not in the layout.

Constraint on MECH-FP-PREMERGE-GC when it is groomed: a revoked entry is not collectible lineage. Collecting it restores exactly the indistinguishability this mechanism removes.

LEFT TO THE OPERATOR, deliberately. This milestone settles the plumbing;
each of these is a rule about how this instance works and milestone five is
where they get written.

- WHEN a signature should be revoked. No trigger, no condition, no policy is stated — the mechanism only defines how a withdrawal is written down and read back.

- Whether a revoked entry should gate. It ships in the non-failing bucket so the mechanism is inert on arrival; membership is one named set (fp-check.py:38) and moving it there is a one-line change the operator's rule can make.

- Who may revoke, and who may lift a revocation by signing over it. Left to DEC-FP-ACCEPT-AUTHORITY, which is still open and is explicitly about grading signing authority rather than about revocation specifically.

- Whether a revocation ever expires, or whether an edge can be revoked more than once with each withdrawal retained. The design keeps one state per edge and no history; a retention rule that wants more is the operator's, and would trip DEC-FINGERPRINT-IN-NODE's RETIRES_ON.

- The tag spelling itself. `revoked` is chosen because it is non-hex and self-describing in a diff; any other non-hex token works identically, and the operator may prefer a different vocabulary once the behaviour model names its moves.
<<<
RELATIONS:
- TYPE: Parent
  VALUE: DEC-FINGERPRINT-IN-NODE
  ROLE: Governed_By
- TYPE: Parent
  VALUE: MECH-FP-CHECK
  ROLE: Assumes

[MECHANISM]
UID: MECH-SDOC-SKILL-CORRECTIONS
TITLE: Correct the sdoc skill and README where they are now false
DEPTH: sketch
AUTHORED_BY: llm
STATEMENT: >>>
Measured while running SPIKE-EXECUTABLE-RULES. The Layout table omits
docs/spec, which holds four nodes. The closing section says there is no
suspect-link detection and no readiness query; fp-check and status.py exist.
File relations accept ROLE at the grammar level -- only REVERSE_ROLE is a
syntax error -- so VALUE only is this corpus's rule, not the parser's. format
and manage take no --output-dir and write ./output in the project. STATUS is
polymorphic: DECISION and SPIKE carry different choices. And the
strictdoc_config.py sys.path line from MECH-SDOC-CONFIG-HOOK-IMPORTABILITY
belongs in the gotcha list.

Two more, both now actionable. The restore block hands a fresh session a bare
strictdoc export while the same file says no devenv shell is needed in the
worktree; that is true of commits only, and a session outside the shell gets
command not found. SLICE-STRICTDOC-OVERLAY put pkgs.ai.devTools.strictdoc in
the devShell, so say the shell is required for strictdoc and not for
committing. And the skill's never invent a UID, run manage auto-uid is
contradicted by every node here: all UIDs are semantic and hand-chosen, and
manage new mints a prefix-plus-counter UID that nobody keeps.
<<<
RATIONALE: >>>
A document that is wrong is worse than one that is silent, which is the
invariant's own argument turned on the document that states it.
<<<
RELATIONS:
- TYPE: Parent
  VALUE: INV-GUARDS-MUST-EXECUTE
  ROLE: Guarantees

[MECHANISM]
UID: MECH-SDOC-EDIT-VIA-MODEL
TITLE: Replace sdoc_edit.py's hand-copied field order with strictdoc's node model
DEPTH: interface-settled
AUTHORED_BY: llm
STATEMENT: >>>
Replace dev/scripts/sdoc_edit.py with dev/scripts/sdoc_model.py, a module over
strictdoc's node model that owns a loaded graph. Three operations:
open_graph(root: Path, *, output_dir: Path | None = None) -> Graph,
Graph.set_field(uid: str, field: str, value: str | None) -> None, and
Graph.save() -> list[Path] returning the files rewritten. set_field validates
before it returns and raises rather than leaving a bad node in the graph; save
writes only the documents whose nodes were touched. Batching is the point: the
graph load is the expensive step and fp-accept signs several UIDs per run.
FIELD_ORDER, find_node_block, find_field_span and render_field all go, and
nothing in the replacement knows the grammar's field order or its block syntax.

The call sequence is fixed by what strictdoc requires. Load with
ProjectConfigLoader.load(input_path=root, output_dir=...) then
TraceabilityIndexBuilder.create(project_config=..., parallelizer=
NullParallelizer(), skip_source_files=True). Reach a node with
index.get_node_by_uid(uid) and its file with
node.get_document().meta.input_doc_full_path. Write a field with
SDocNode.set_field_value(field_name=..., form_field_index=0, value=...), where
value=None deletes the field. Check the node with SDocValidator.validate_node(
node, document_grammar=doc.grammar, path_to_sdoc_file=...). Serialise with
SDWriter(project_config).write(document) and replace the file with that string.

Three obligations sit on the module because strictdoc does not carry them.
Value validation: set_field_value accepts anything, so an invalid SingleChoice
and the deletion of a required field both reach disk and are caught only by a
later parse -- validate_node is the catchable gate and costs about 20 us.
Delimiter rejection: a value containing a line that begins at column zero with
"<<<" serialises to a file that cannot be re-parsed, and validate_node does not
see it, so set_field rejects such values itself. Path discovery: the model
supplies each node's source file directly, replacing fp-accept's glob-and-grep
scan for a "UID: " line.

Out of scope, each belonging to a named sibling: the verb and flag surface, UID
minting and node creation (SLICE-SDOC-CLI); refusing writes to operator-owned
fields (MECH-RUNTIME-WRITE-GUARD); relocating the cache
(MECH-SDOC-CACHE-DIR-FOR-WORKTREES); trimming the format set
(MECH-SDOC-LEAN-FORMATS). fp-check keeps reading the JSON export; this changes
the write path only.
<<<
RATIONALE: >>>
The copied order list matches the grammar today, and the wrapper will need field
writes for every field rather than one, so generalising a hand-copied list is the
wrong direction when strictdoc already owns the order. The larger gain is that
going through the model collapses find, edit and format into one path: the model
knows each node's file, so the glob-and-grep scan disappears, and SDWriter
produces the canonical form, so the "run strictdoc format afterward" step in
fp-accept's docstring disappears with it. That is what SLICE-SDOC-CLI means by
formatting applied by the same code path.

Owning validation on this side is not a tax the model API imposes; it is the
finding that makes this node necessary rather than tidy. set_field_value is a
mutator with no opinion about the value, so a wrapper that only swapped in the
API would be strictly less safe than the text editor it replaces, which at least
could not produce an invalid choice by accident.
<<<
NOTES: >>>
Measured on strictdoc 0.28.3 against a scratch copy of this repo's nine
documents; nothing was written in the checkout.

Grammar resolution. A single-document parse leaves elements_by_type at ["TEXT"]
and set_field_value raises KeyError("MECHANISM"); after
TraceabilityIndexBuilder.create it holds all six element types and
element.field_titles for MECHANISM is exactly the grammar's list. The @repo
alias is resolved in traceability_index_builder.py:421-446 through
project_config.grammars, not by the reader.

The previous statement said the whole graph is required. It is not, and the
correction matters because the cheap path looks like it works. SDocGrammarReader
().read_from_file(...) plus document.grammar.update_with_elements(g.elements)
makes set_field_value work off a single-document parse (0.43 s parse, 7 ms
grammar) and for 99-backlog.sdoc produces a byte-identical 130839-byte write.
It drops the TEXT element the builder back-fills at
traceability_index_builder.py:447-456: on a probe document carrying free text
that the corpus exports clean (exit 0), the hand-stitched path raises
KeyError("TEXT") on the TEXT node. Use the builder.

Timings, one process, NullParallelizer: cold index build 1.44 s, warm 0.11 s,
warm rebuild after one changed file 0.97 s; three set_field_value calls 36 us;
SDWriter.write of the 2820-line, 130839-byte 99-backlog.sdoc 0.8 ms;
validate_node 8-22 us; SDReader re-parse of that document 0.37 s; the whole
set-validate-write-reparse-save cycle 0.34 s. Config construction alone is
0.67-0.81 s of every number here, which is MECH-SDOC-LEAN-FORMATS's lever.

Field order holds under abuse. On a node stripped of RATIONALE, PARENT_FP and
NOTES, setting them in the order NOTES, PARENT_FP, RATIONALE serialises them
RATIONALE, PARENT_FP, NOTES. Round trip is byte-stable: loading all nine
documents and writing every one back unmodified changes no file, and a
single-field edit produces a diff confined to that node.

One visible difference from the text editor. Single-line versus block form comes
from the grammar, not from what was parsed -- is_field_idx_multiline
(grammar_element.py:410) makes every String field after TITLE multiline -- so a
PARENT_FP written through the model is always a >>> block. Existing single-entry
values in the corpus are inline (01-tooling.sdoc:85) because format preserves
each parsed field's own flag, so re-signing such a node reflows it. Cosmetic
only: sdoc_fp.py:32 excludes PARENT_FP from the contract hash, so no fingerprint
churns.

What set_field_value accepts silently, each confirmed by a clean full export
exiting 1 where the unmutated corpus exits 0: DEPTH "totally-not-a-depth"
("invalid SingleChoice value"), AUTHORED_BY "robot", and value=None on a
required STATEMENT ("Node is missing a field that is required by grammar").
validate_node catches all three plus a newline inside a single-line choice
field, raising StrictDocSemanticError. It does not catch a "<<<" line inside a
multiline value. Only a line starting at column zero with "<<<" terminates a
block: "  <<<", "a<<<b", ">>>" and a literal "[MECHANISM]" line all survive the
round trip intact, so the reject rule is one regex. An unknown field name fails
closed but unhelpfully, as ValueError("list.index(x): x not in list").

Do not validate by rebuilding the index. TraceabilityIndexBuilder.create prints
and calls sys.exit(1) on a semantic error (traceability_index_builder.py:394,
470, 527), so it is a process exit, not an exception carrying detail.

SDWriter, SDReader and SDocValidator are not exported from strictdoc.api; of
what this needs, only TraceabilityIndexBuilder, ProjectConfigLoader,
Parallelizer, SDocNode, SDocDocument, TraceabilityIndex and DocumentTreeError
are. The module takes three internal imports, which the pinned overlay makes
tolerable and a version bump should re-check.
<<<
RELATIONS:
- TYPE: Parent
  VALUE: DEC-FINGERPRINT-IN-NODE
  ROLE: Governed_By

[MECHANISM]
UID: MECH-FILE-RELATION-EXISTENCE
TITLE: File relations to nonexistent paths export clean
DEPTH: interface-settled
AUTHORED_BY: llm
STATEMENT: >>>
Check every File relation against the repository tree in
dev/scripts/file-check.py, built in cycle-check.py's shape: it reuses
sdoc_fp's load_index and iter_nodes, prints every finding with its node UID
and owning document title, and exits non-zero when there is one. Its argv is
the export JSON plus the repository root, a second argument neither
cycle-check.py nor fp-check.py takes, because the JSON export carries no path
for anything and so offers nothing to resolve against.
checks/strictdoc-file-check.nix runs it over the flake source beside the
cycle and fingerprint checks, which puts it in nix flake check.

A VALUE is well-formed in exactly one shape: a normalized POSIX path relative
to the repository root, not absolute, with no leading ./ and no .. segment.
Any other shape is a finding in its own right rather than a path to normalize
and then resolve. The target must be an existing regular file; a directory is
a finding. That rule is upstream's, not ours -- strictdoc's own
file-traceability validation accepts precisely this shape and rejects ./x,
../x, an absolute path and a directory with the same message -- so holding to
it keeps the corpus able to turn that feature on later.

The sdoc CLI checks only the VALUEs it is about to write, applying the same
well-formedness rule plus one stat: microseconds, not a whole-graph pass. The
corpus-wide gate stays alongside it, because a write-time check cannot see a
file deleted or moved after its relation was written, and that is the
direction the ghost problem actually runs.

Two exclusions, both deliberate and both cheap to reverse. Targets outside
the repository are not supported; no File relation names one today. Forward
references are not supported either -- a node may not name a path its own
unbuilt work will create. All three File relations in the corpus sit on
implemented nodes, so the strict rule costs nothing now, and relaxing it
later by gating existence on DEPTH is a one-line change, where tightening it
later would not be.
<<<
RATIONALE: >>>
This node's own earlier premise -- that the parser will not do it -- is
refuted. StrictDoc validates File relations exactly this way, but only when
REQUIREMENT_TO_SOURCE_TRACEABILITY is in project_features, which this project
does not set. Enabling it is one config line, and it was rejected on three
measurements rather than on taste. It costs 12.32 s against 1.52 s on this
890-file tree, and that cost lands on every export, including the whole-graph
validation the sdoc CLI runs per write, which is budgeted at about a second.
It reports one broken relation per run, so N defects cost N runs of 12 s. And
its predicate is "is an indexed source file", not "exists": a File relation
naming a file that is present but binary is reported as not existing. A
checker over the JSON export has the exact predicate, reports every finding
in one pass, and costs 0.03 s.

The defect itself is worth closing rather than tolerating because a design
that claims code which no longer exists is the ghost problem the File role
was adopted to catch.
<<<
NOTES: >>>
Measured 2026-08-27 on a scratch copy of the tree, strictdoc 0.28.3
(/nix/store/cck3q51nd32dpbmpkwv5xpkxxhpnr2ak-strictdoc-env), every export
into a clean output directory.

The defect, and a positive control for the same harness:

- A File relation with VALUE packages/semble/lib/doesNotExist.nix exports
  with exit 0, emits no warning line at all, and the dead path survives
  verbatim into index.json.
- Replacing it with a dangling NODE relation fails the identical export with
  exit 1 and "references parent requirement which doesn't exist"
  (traceability_index_builder.py:663). The export gate is alive; it just does
  not cover File.
- Prototype checker over the JSON export: 0.03 s, exit 1, all three injected
  broken relations named in one run. Negative control on the unmodified
  corpus: 3 File relations checked, 0 broken, exit 0 -- both on the scratch
  copy and on the real graph.

Upstream's own check, measured by adding
project_features=["REQUIREMENT_TO_SOURCE_TRACEABILITY"] to the scratch
strictdoc_config.py:

- Broken path: exit 1, "Requirement MECH-FILE-RELATION-EXISTENCE references a
  file that does not exist" (file_traceability_index.py:615).
- Accepted forms, probed exhaustively: packages/semble/lib/withGrammars.nix
  passes, while ./packages/semble/lib/withGrammars.nix,
  packages/semble/lib/../lib/withGrammars.nix,
  ../../../packages/semble/lib/withGrammars.nix, /etc/hostname, the directory
  packages/semble, and a document-relative 01-tooling.sdoc all fail.
  Resolution is a string lookup in the indexed-source-file map keyed by a
  POSIX path relative to source_root_path -- not filesystem resolution --
  which is why every non-normalized form fails while naming a real file.
- A file that exists but is not indexed reports the same "does not exist":
  measured on a .pyc and on a file containing a NUL byte, both skipped as
  binary. A plain .txt passes.
- Cost on the whole repo, 890 tracked files and 885 source tasks: 1.52 s off,
  12.32 s on, 244 MB maxrss. Narrowing include_source_paths to
  packages/semble/** drops it to 1.84 s and 16 tasks, but then
  dev/scripts/cycle-check.py -- which exists -- is reported as not existing.
  Narrowing trades cost for false positives and is not viable.
- One error per run: three broken relations across two nodes produced one
  error line, and it named the second node's.
- The JSON export is byte-identical with the feature on and off, so enabling
  it would not perturb cycle-check or fp-check.

Two traps found while measuring, neither confined to this node:

- ProjectConfig(project_features=[...]) REPLACES the defaults (TABLE_SCREEN,
  TRACEABILITY_SCREEN, DEEP_TRACEABILITY_SCREEN, SEARCH) rather than adding
  to them. The JSON export is unaffected -- measured identical -- but the
  HTML screens would be lost.
- StrictDoc's own grammar source calls this role experimental: "FileReference
  is an early, experimental feature. Do not use yet."
  (backend/sdoc/grammar/type_system.py:25).

The check's repository-root argument comes from the flake source in the check
derivation, following checks/strictdoc-cycle-check.nix's
"strictdoc export ${self}". That is the git-tracked tree, so a File relation
naming an untracked file passes locally and fails in CI -- correct behaviour,
but the failure appears at a distance from the edit.

sdoc_fp.iter_nodes walks only each document's top-level NODES and does not
recurse into sections. A recursive walk finds the same 3 File relations on
today's corpus, so the two are currently equivalent; use iter_nodes for
consistency with the other two checkers and fix it in one place if sections
ever nest nodes.
<<<

[SPIKE]
UID: SPIKE-DECISION-ACCEPTANCE-PATH
TITLE: Who moves a DECISION from open to accepted, and how
DEPTH: sketch
AUTHORED_BY: llm
STATUS: unrun
RETIRES_ON: >>>
The first open-to-accepted transition is made on this branch with its actor
and its trigger recorded, or the README states the path outright.
<<<
STATEMENT: >>>
No open-to-accepted transition has ever occurred on this branch: every
accepted decision was born accepted, and the one exit from open was
open-to-superseded. The README says a planning session grooms, decides and
slots, and also that decisions come to the operator as plain-language cards;
the skill does not say who turns STATUS. DEC-LONG-LIVED-BRANCH's acceptance
language is about signing, not STATUS. The transition drawn in every state
machine is inferred from the enum, not observed.
<<<
RATIONALE: >>>
A transition that exists only in the enum is the kind of gate that gets
guessed at. Observing it once settles who owns it.
<<<
RELATIONS:
- TYPE: Parent
  VALUE: DEC-LONG-LIVED-BRANCH
  ROLE: Governed_By

[MECHANISM]
UID: MECH-SEMANTICS-DEFINITION-BOUNDARY
TITLE: Draw the boundary between defining semantics and this system's semantics
DEPTH: sketch
AUTHORED_BY: llm
STATEMENT: >>>
Two layers, framed by the operator on 2026-08-25. The definition layer is how
the semantics of any model are defined: a grammar; the state transitions over
its fields; the gates on those transitions; the triggers that fire them; the
flows that hit them; where validators wire in and which hook point each one
belongs to; which validations run on CRUD-like operations versus commit and
merge operations; and how a grammar maps to structured CLI arguments. The
instance layer is this design system's particular semantics: fingerprints,
contracts, the ripple, DEPTH, signing authority.

CRUD and git operations blur the line. They are assumed to be part of the
semantic vocabulary and need a placement in the definition layer.

TODO: define that boundary in docs/spec where it belongs, and link code to
the layer it belongs to with parent and child relations against the boundary
nodes, so an implementation of semantics is never mistaken for the definition
of semantics.
<<<
RATIONALE: >>>
SPIKE-EXECUTABLE-RULES answered at the instance layer while the operator was
asking at the definition layer. The two are easy to conflate because the
instance is the only worked example, and conflating them is how a meta-model
ends up shaped by one implementation's preferences.
<<<
RELATIONS:
- TYPE: Parent
  VALUE: DEC-SYSTEM-PURPOSE
  ROLE: Governed_By

[MECHANISM]
UID: MECH-SDOC-CACHE-DIR-FOR-WORKTREES
TITLE: Put strictdoc's cache directory where a worktree hook does not scan it
DEPTH: interface-settled
AUTHORED_BY: llm
STATEMENT: >>>
strictdoc_config.py's create_config() passes dir_for_sdoc_cache="$TMPDIR" to ProjectConfig. That exact literal is a sentinel strictdoc expands to <tempfile.gettempdir()>/strictdoc_cache/<md5 of os.getcwd()>/<strictdoc version>, so every worktree gets its own cache outside its own checkout, keyed by the directory the command ran in. That one keyword argument is the whole change. No devenv wiring, no wrapper, no environment variable, no new option.

It covers the parse cache written by every command, export, format, manage and server alike, because the expansion happens in ProjectConfig.__init__ and every entry point builds one. It does not cover the export ARTIFACT directory: a bare strictdoc export . still writes ./output/json, so the output/ line in .gitignore stays. The change stops the 3.8 MB of _cache landing under it, not the directory itself.

Two constraints bind the tool that consumes this. The cache path is keyed on the cwd at the moment ProjectConfig is constructed, so the CLI chdirs to the project root before constructing it. And each cached parse is keyed on the output directory concatenated with the input path, so a warm cache also needs one stable --output-dir; a fresh output directory is a cold parse cache and leaves behind a second full set of entries.
<<<
RATIONALE: >>>
The cache is the only thing strictdoc writes into the checkout that nobody asked for, and it got in once already: commit 893009a0 records a git add -A staging the parse cache and cspell reporting 2591 issues over it. That same commit closed the route by gitignoring output/, which is why nothing fails today. What remains is 3.8 MB of untracked files inside a worktree defended by an ignore rule, in a repository where the standing advice is to run git add -A and where the sdoc skill has to carry a warning about it. Moving the writer is cheaper than maintaining the exclusion, and it is one line.

The $TMPDIR sentinel rather than a hand-picked absolute path because the cached parses are per-file but the dependency map is a single file per cache directory, so worktrees pointed at one fixed path would overwrite each other's. The sentinel's md5-of-cwd component gives each worktree its own directory with no per-worktree configuration to keep in sync.
<<<
NOTES: >>>
Measured 2026-08-27 against strictdoc 0.28.3, on a scratch copy of the corpus, never in the tree.

STRICTDOC_CACHE_DIR is worse than inert. project_config.py:244 asserts it equals exactly "Output/_cache" -- capital O, which the earlier draft of this node got wrong. Lowercase output/_cache aborts too, with the bare message "error: output/_cache" and no explanation. The branch is checked BEFORE the config value (241-245 versus 246-251), so it overrides dir_for_sdoc_cache: with the config already set to "$TMPDIR", STRICTDOC_CACHE_DIR=Output/_cache put the cache back inside the checkout at ./Output/_cache/0.28.3. It is not a relocation lever, it is a way to undo this mechanism. Nothing in this repository sets it.

Which commands dirty the checkout today: format . creates ./output/_cache/<version>/ with 11 files. Only integrate_server_config and integrate_export_config move the cache into the output directory (project_config.py:716 and 755), and they fire only because the default value startswith "output/_cache"; format and manage have neither hook nor --output-dir. So export --output-dir <elsewhere> never dirtied the checkout, and the 3.8 MB in the current worktree, holding 0.28.2 and 0.28.3 side by side, is from format and manage runs.

After the change --output-dir no longer moves the cache, because the expanded value is absolute and fails that startswith guard. Measured: export --formats=json --output-dir <scratch> left ./output absent and wrote /tmp/strictdoc_cache/<md5>/0.28.3.

Positive control that the relocated cache is read and not merely written: on this 10-document corpus export costs 1.87 to 1.92 s cold and 1.32 to 1.57 s warm at a stable output directory. A brand-new output directory against the same warm cache directory costs 2.04 s, then 1.51 s -- because pickle_cache.py:127 keys each entry on output_dir + the input path. Three output directories left 27 entries for 9 sdoc files. Nothing prunes them, and the version component means a strictdoc bump strands the old tree; that is true today as well, just in /tmp instead of the checkout.

The one file shared within a cache directory is <cache>/dependencies (file_dependency_manager.py:36). It is written even by a json-only export but read only by the HTML generator's must_generate, so with formats pinned to SDoc and JSON (MECH-SDOC-LEAN-FORMATS) nothing consumes it.

TMPDIR is unset on this machine and /tmp is mode 1777, so the path is world-writable and predictable while pickle_cache.py:38 unpickles without validation. Not a concern on a single-user laptop; on a shared host, set TMPDIR.

Not proven either way: the sdoc skill's "incremental export produces false greens" gotcha did not reproduce on 0.28.3 for a syntax break -- an unknown field appended to 99-backlog.sdoc gave exit 1 on a fresh output directory, on a reused one, and on repeats, both before and after the change. So the relocation is measured not to INTRODUCE a false green for that break class, and the original gotcha is unreproduced rather than refuted. See the SPIKE proposed alongside this node.

Lands with MECH-SDOC-LEAN-FORMATS: same file, same function, both single keyword arguments. Two things go stale in the same commit -- the sdoc skill's line that "format and export write a cache into ./output/ by default", and any existing output/_cache directories, which the change should delete rather than leave as orphans of a version that no longer writes there.
<<<

[MECHANISM]
UID: MECH-OVERLAY-PYTHON-OVERRIDE-SEAM
TITLE: Record overridePythonAttrs as the third override seam in the overlay fragment
DEPTH: sketch
AUTHORED_BY: llm
STATEMENT: >>>
dev/fragments/overlays/overlay-pattern.md teaches two override seams and a
rule for choosing between them: a thin overrideAttrs for a builder that reads
version and src as ordinary attrs, and .override on the BUILDER for a
lib.extendMkDerivation one that consumed an argument to derive an attr. It
never mentions overridePythonAttrs, which is the correct seam for a
buildPythonPackage and is what two packages here already use --
overlays/git-tools/git-revise.nix and, since SLICE-STRICTDOC-OVERLAY,
overlays/dev-tools/strictdoc.nix.

The INPUT-versus-OUTPUT rule the fragment already states decides this case
too: buildPythonPackage consumes `dependencies` and `pythonRelaxDeps` as
arguments, so overrideAttrs lands them as dead attrs nothing reads, exactly
like an overridden npmDepsHash. Add the seam and cite the rule rather than
writing a third independent one.
<<<
RATIONALE: >>>
A pre-existing gap, not one this slice opened -- git-revise predates it. It
surfaced while writing the strictdoc overlay, where the fragment was read for
the seam decision and did not answer, and the answer had to be re-derived from
the nixpkgs source. The next Python package pays that cost again.

overlays/README.md now carries the seam in its source-pattern bullets, which
is where an overlay author looks; the dev fragment is where an AGENT looks,
and it is the one still silent.
<<<
NOTES: >>>
Filed as issue #1267, self-contained, on 2026-08-25. That issue is the
user-visible tracker; this node is the design-graph record of which slice found
it. Close both together.

One of the two worked examples cited above is GONE as of 2026-08-27:
overlays/dev-tools/strictdoc.nix uses no override seam at all now, having become
a plain attrset extension of upstream's flake package
(MECH-STRICTDOC-UPSTREAM-FLAKE). overlays/git-tools/git-revise.nix is still the
example, the gap in dev/fragments/overlays/overlay-pattern.md is unchanged, and
#1267 is still the tracker -- the finding lost a citation, not its subject.
<<<

[MECHANISM]
UID: MECH-STRICTDOC-CLOSURE-TRIM
TITLE: Drop the three strictdoc dependencies that cost closure and are unused
DEPTH: sketch
AUTHORED_BY: llm
STATEMENT: >>>
SPIKE-EXECUTABLE-RULES measured six dependencies in nixpkgs' strictdoc
expression that upstream's pyproject.toml does not declare. Three of them --
graphviz, pybtex and setuptools -- cost closure; the other three return
through html2pdf4doc, so removing them buys nothing. Removing the three is a
`dependencies` filter in overlays/dev-tools/strictdoc.nix.

Deliberately NOT done as part of SLICE-STRICTDOC-OVERLAY, whose shape is a
thin override that leaves the dependency set upstream-owned. Trimming it is a
separate, arguable change: it makes this package diverge from nixpkgs in a way
a version bump cannot re-converge, and the win is closure size on a package
every session already has.
<<<
RATIONALE: >>>
Recorded so the measurement is not re-run. If it is picked up, verify the
six-and-three split against the release in the sidecar rather than trusting
this node -- it was measured against 0.27.1 and the dependency list moved in
0.28.
<<<
NOTES: >>>
CHANGED SHAPE 2026-08-27, by MECH-STRICTDOC-UPSTREAM-FLAKE, and there is no
sidecar to verify against any more. The measurement was taken against nixpkgs'
strictdoc expression, and this repository no longer builds from it: the package
is upstream's own uv2nix build from their uv.lock. There is no `dependencies`
filter to apply and no first-party override to hang one on, so the six-and-three
split describes a derivation nothing here evaluates.

If closure size is still worth chasing it is now a question for upstream's own
flake, which puts it outside this repository and probably outside this plan.
<<<

[MECHANISM]
UID: MECH-REQIF-PIN-HAS-NO-SWEEP
TITLE: Decide what keeps the inline reqif pin current
DEPTH: sketch
AUTHORED_BY: llm
STATEMENT: >>>
overlays/dev-tools/strictdoc.nix pins reqif inline at 0.1.0, because
mkUpdateScript rebuilds the sidecar from scratch on every write and would
erase a second package's pin parked there. Nothing sweeps that pin.

The failure is asymmetric and only half of it is loud. A strictdoc release
that outgrows the pin fails the BUILD, because the release's own constraint is
checked at build time -- that half is fine. But reqif moving on its own leaves
the pin quietly behind, and once the nixpkgs pin reaches 0.1.x the override
keeps shadowing it with an older release for no reason at all.

Three shapes, none argued yet: give reqif its own tracked overlay row; branch
on lib.versionOlder so the override disappears when nixpkgs catches up; or
accept the staleness and say so in the overlay. The third is what is in force
today by default rather than by decision.
<<<
RATIONALE: >>>
This is the transitive-hash gap wearing different clothes -- the same
"ghArchiveUpdateScript refreshes only the src hash" root cause that forces a
Rust package to derive cargoDeps from the pinned src. A Python dependency is a
separate derivation rather than a hash, so the Rust answer does not transfer
and the question stays open.
<<<
NOTES: >>>
MOOT 2026-08-27, by MECH-STRICTDOC-UPSTREAM-FLAKE. There is no inline reqif pin
any more, and no sidecar for one to live in: overlays/dev-tools/strictdoc.nix
re-exports upstream's flake package, and its uv2nix set resolves reqif from
upstream's own uv.lock at the artifact the release was tested against. All three
shapes offered above are answered by not having the problem.

The ROOT CAUSE is not moot and is not this node's to carry: an update script
that refreshes only the src hash still leaves a transitive pin unswept for every
package that parks one, which is the standing transitive-hash gap.
<<<

[MECHANISM]
UID: MECH-README-ROWS-FOLLOW-DESCRIPTIONS-NOT-PACKAGES
TITLE: Make a package with no description fail rather than vanish from the README
DEPTH: sketch
AUTHORED_BY: llm
STATEMENT: >>>
dev/generate.nix's mkDescriptionRows maps over dev/data.nix's description
attrsets, not over the overlay's package set, so a package with no description
entry is silently absent from the generated README table. Nothing fails: not
the generator, not nix flake check, not the drift check, which compares the
generated file against the same incomplete input.

Fix shape: derive the row set from the overlay group and look each description
up, so a missing one throws with the package's name. That inverts the failure
from a silent omission into an eval error naming exactly what to write.
<<<
RATIONALE: >>>
Found while landing SLICE-STRICTDOC-OVERLAY: the package was registered in
overlays/default.nix, config.update.targets and the cache-hit-parity registry
-- three surfaces that DO fail when incomplete -- and would still have shipped
absent from the public README, because the fourth surface is a lookup table
nothing cross-checks. The three loud registries are why this was caught at all,
and they are the model for the fix.

Not scoped to this plan's subject. Recorded here because it was found here and
there is no other parking lot; move it if the repo grows one.
<<<
NOTES: >>>
Filed as issue #1266, self-contained, on 2026-08-25 -- the parking lot the
rationale above asks for. That issue is the user-visible tracker; this node is
the design-graph record of which slice found it. Close both together.
<<<

[MECHANISM]
UID: MECH-READINESS-REPORT-FRONTIER
TITLE: Report the readiness frontier, not the whole closure
DEPTH: sketch
AUTHORED_BY: llm
STATEMENT: >>>
status.py seeds its closure walk with the slice itself, so a slice below
interface-settled reports itself as its own blocker: SLICE-FIRST-CONVERSION
prints "blocked by SLICE-FIRST-CONVERSION" and nothing else. Not designed yet
and blocked on a dependency call for different actions and should not read the
same.

The walk then appends every unsettled node in the transitive closure, so
SLICE-INSTANCE-SEMANTICS-MIGRATION lists twenty-three blockers, most reachable
only through another blocker. What a reader can act on is the frontier: the
unsettled nodes whose own dependencies are all settled. The rest follow.

Fix shape: separate the slice's own DEPTH from its dependency blockers in the
output, and print the frontier with a count of what sits behind it.
<<<
RATIONALE: >>>
The readiness query is the only view that says what to work on next, and at
twenty-three undifferentiated lines it says nothing. Distinct from
MECH-READINESS-PREDICATE-RECONCILE, which is about five definitions of ready
disagreeing; this is one predicate reported unusably.
<<<
RELATIONS:
- TYPE: Parent
  VALUE: DEC-LOCAL-IMPLEMENTABILITY
  ROLE: Governed_By

[MECHANISM]
UID: MECH-GRAMMAR-TEXT-ELEMENT-INJECTION
TITLE: Our grammar declares no TEXT element, so strictdoc silently adds one
DEPTH: sketch
AUTHORED_BY: llm
STATEMENT: >>>
When an imported grammar declares no TEXT element, strictdoc inserts a default
one at position zero rather than reporting anything. Our grammar declares five
elements and none of them is TEXT, so the in-memory grammar has six.

Benign today because the file is hand-written and nothing round-trips it. It
stops being benign at SLICE-GRAMMAR-FROM-NIX, whose acceptance is a
byte-identical regenerated grammar: anything that reads the grammar and writes
it back -- strictdoc's own writer, a format pass, a round-trip test -- emits the
injected element too, so a naive round-trip comparison fails against a file
that was never wrong.

Decide whether the generated grammar declares TEXT explicitly, which makes the
in-memory and on-disk forms agree, or whether the byte-identity check compares
generator output against the file and never round-trips through strictdoc.
<<<
RATIONALE: >>>
An injected element is invisible in every artefact a person reads, so the first
encounter is a byte-identity check failing for a reason the diff does not
explain.
<<<

[MECHANISM]
UID: MECH-ASTGREP-OVER-SDOC
TITLE: ast-grep could match sdoc files directly using the grammar we already package
DEPTH: sketch
AUTHORED_BY: llm
STATEMENT: >>>
ast-grep is tree-sitter based and takes custom languages through a dynamic
tree-sitter library. This repository already packages a patched
tree-sitter-strictdoc for semble, so the grammar half of that already exists
and is already maintained.

That makes structural matching over sdoc documents available without writing a
parser: find every node carrying a given field value, rewrite a field across a
corpus, lint for a shape the strictdoc grammar cannot express. Relevant to the
milestone that makes a tool the only writer of sdoc files, where the
alternative is driving strictdoc's own node model for every edit.

Unproven. Registering a custom language with ast-grep needs the grammar built
as a shared library with the right entry point, which the semble packaging may
or may not already produce.
<<<
RATIONALE: >>>
Noted while measuring ast-grep for the grammar milestone's conversion pass.
Two capabilities this repository already carries separately turn out to
compose, and nothing records that they might.
<<<

[MECHANISM]
UID: MECH-GRAMMAR-EXTRACT-SOURCE-BOUNDARY
TITLE: The overlay that put the extractor's sources on the wrong side is gone
DEPTH: implemented
AUTHORED_BY: llm
STATEMENT: >>>
dev/fragments/overlays/overlay-pattern.md states an invariant: an overlay must
not import build sources from packages/, because that outbound edge prevents
lifting the overlay tree as a clean directory move. The two worked examples,
overlays/kiro-memory-distiller/ and overlays/mcp-servers/openmemory-mem/, both
keep their repo-local sources beside the derivation that consumes them.

The grammar milestone's layout puts the extractor's three Python entry points
under packages/strictdoc-grammar/extract/ while exposing the runner at
pkgs.ai.devTools.strictdoc-grammar-extract, so wiring the entry points into the
derivation would create exactly that edge.

overlays/dev-tools/strictdoc-grammar-extract.nix therefore ships only the
environment -- an interpreter carrying strictdoc's dependency closure, its
site-packages on PYTHONPATH, and ast-grep on PATH -- and takes the entry point
as its first argument. It works, and it is not the intended shape.

Two ways out, both one small edit. Relocate the entry points under
overlays/dev-tools/strictdoc-grammar-extract/ and add src plus an --add-flags
line, which honours the invariant and splits the package's sources from its
generated output. Or record an exemption to the invariant for generation-time
tooling and point src at packages/, which keeps the package's four surfaces
co-located and admits one overlay-to-packages edge.

Nothing enforces the invariant mechanically; there is no check, and no such
edge exists in the tree today.
<<<
RATIONALE: >>>
Noted while scaffolding the grammar package. A partial wiring that works is the
kind of thing that stops being noticed once the logic lands on top of it, and
the choice belongs to whoever owns the overlay taxonomy rather than to the
session that tripped over it.
<<<
NOTES: >>>
RULED by the operator 2026-08-26: the invariant was read the wrong way round.
It is correct that an overlay should be the faithful conversion of upstream, but
the conclusion is not that sources must move under overlays/ -- it is that the
WRAPPING does not belong in an overlay at all. It belongs in a module. See
MECH-STRICTDOC-DEVENV-MODULE for where it goes, and
MECH-OVERLAY-WRAPPING-BELONGS-IN-MODULES for the repo-wide version of the same
mistake.

IMPLEMENTED 2026-08-27, and by NEITHER of the two ways out the statement above
lists. Both of those assumed the wrap survives somewhere and only argued about
where its sources sit. The ruling says it does not belong in an overlay at all,
so overlays/dev-tools/strictdoc-grammar-extract.nix was DELETED rather than
thinned and pkgs.ai.devTools.strictdoc-grammar-extract no longer exists. The
outbound overlay-to-packages edge is gone because the overlay is gone, not
because anything moved to satisfy the invariant.

packages/strictdoc-grammar/lib/mkExtract.nix is now the only copy. It is a
factory rather than inline module code because it has two consumers that are
not each other: ../modules/devenv puts it in the dev shell, and flake.nix builds
it ONCE for the strictdoc-grammar-* checks, which run the same entry points in a
derivation with no module system in sight. Measured at the move: the wrapper's
store path is unchanged, and devenv's package list carries exactly one copy.

One consequence, recorded because it is what wrapping in a module MEANS rather
than a side effect of this edit. Build inputs now come from the CONSUMER's pkgs
instead of an overlay's isolated ourPkgs. That is only safe here because the
part that has to agree with upstream's virtual environment is upstream's own
interpreter, and the single spliced import (ast_grep_py) is guarded by the
wrapper's install check.

The repo-wide version of the same mistake is untouched and still open:
MECH-OVERLAY-WRAPPING-BELONGS-IN-MODULES, and
MECH-AGENTS-INFER-OVERLAY-CONVENTION-FROM-EXAMPLES for why writing the rule
down again is not the remedy.
<<<

[MECHANISM]
UID: MECH-DSL-NAMED-CONSTRUCTORS-DO-NOT-SPAN
TITLE: The DSL's named constructors cover the common case, not the relation space
DEPTH: sketch
AUTHORED_BY: llm
STATEMENT: >>>
The settled DSL shape gives rel.parent and rel.child two positional roles, and
rel.file as a bare value carrying none. The grammar allows more than that in
both directions: ROLE and REVERSE_ROLE are optional on Parent and Child, so a
role-less parent relation is legal, and File takes a ROLE even though it has no
REVERSE_ROLE production at all.

So the three named constructors between them cannot write two shapes the
grammar accepts. Both are reachable through the generic rel.mk -- rel.mk
"parent" {} and rel.mk "file" {role = "Depends";} -- and the types accept both,
so nothing is unwritable. What is missing is a named way to say it.

Whether that matters depends on whether the DSL is meant to be the readable
surface for every legal grammar or the fast path for the common one. The same
question applies to HUMAN_TITLE, which no field constructor names either.
<<<
RATIONALE: >>>
Noted while implementing the DSL against the settled shape. The gap is easy to
mistake for an oversight and rewrite, and the fix -- more arities, or optional
attrset arguments -- costs the property that every constructor is currently a
one-line attrset literal.
<<<

[MECHANISM]
UID: MECH-DSL-CHECKS-NOTHING-BY-ITSELF
TITLE: DSL values are unchecked until something feeds them to the option surface
DEPTH: sketch
AUTHORED_BY: llm
STATEMENT: >>>
The DSL is sugar only, which means it asserts nothing: every constructor is a
plain attrset literal, and the sole thing that can reject a malformed value is
the normalized option surface it is checked against. Measured by evaluating the
DSL with its normalized argument bound to a throw -- every constructor still
worked, including the ones building values the surface rejects.

That is the intended design, and it has a consequence worth stating. The
barrel declares a dsl to normalized dependency edge that does not exist at
evaluation time, so a consumer that imports the DSL and hands the result
straight to the emitter passes through no type at all. The emitted file would
then be checked only by strictdoc, at export, where the two silent duplicate
cases are known not to fire.

The guarantee therefore lives entirely in the consumer's option declaration.
Either the emitter's entry point takes values already checked -- by declaring
its input with the normalized type rather than accepting a bare attrset -- or a
consumer can bypass the surface without noticing.

CONFIRMED by measurement in the repair step of the same milestone, which is why
this node is not filed a second time under another name. Rendering values.nix
and fixtures/foreign.nix through `emit.grammar` directly -- not through
lib/check.nix -- produces bytes IDENTICAL to both committed files, and with
check.elements gutted to the identity function the model-equal, foreign-roundtrip
and negative-fixtures checks all stayed GREEN. The emitter reads every key with
an `or` default, so it is blind to every weakening the types catch. lib/check.nix
now exists and checks/strictdoc-grammar-surface-live.nix gates it, but the bypass
itself is still reachable: nothing stops a consumer calling emit.grammar.
<<<
RATIONALE: >>>
Noted while proving the DSL cannot weaken the types. It cannot, but "cannot
weaken" is a statement about a value that reaches the surface, and nothing in
the current wiring guarantees one does.
<<<

[MECHANISM]
UID: MECH-SGRA-ADMITS-NO-COMMENTS
TITLE: A .sgra file cannot carry a generated-file header, because it has no comment syntax
DEPTH: sketch
AUTHORED_BY: llm
STATEMENT: >>>
The grammar for .sgra files admits nothing before [GRAMMAR] and nothing between
its keys. A leading # line fails the textx parse at 1:1 with
Expected '[GRAMMAR]', and there is no alternative comment production anywhere in
the file. Measured against strictdoc 0.28.3.

Every other generated artefact in this repository opens with a line saying it is
generated and naming its generator. A .sgra emitted by the grammar surface
cannot, so docs/sdoc/grammar.sgra will look hand-written forever and a session
editing it by hand gets no warning at the point of editing. The only places a
banner could hide are a field HUMAN_TITLE or an element PREFIX, both of which
change what the file means.

Whatever marks the file as generated therefore has to live outside it -- a
sibling README, a treefmt or check rule that regenerates and diffs, or a path
convention. Undecided which.
<<<
RATIONALE: >>>
Noted while building the negative fixture corpus, where the same limitation
forced the per-fixture expectation out of the fixture files and into their
README.
<<<

[MECHANISM]
UID: MECH-JSON-EXPORT-DROPS-GRAMMAR-DETAIL
TITLE: The JSON export flattens the grammar it reports, so it cannot verify an emitted .sgra
DEPTH: sketch
AUTHORED_BY: llm
STATEMENT: >>>
strictdoc export --formats=json reports a DOCUMENTS[].GRAMMAR block, and that
block is lossy in four ways. Measured on 0.28.3 against a grammar that uses all
four of them.

Every field TYPE is reported as the string "String" -- a Tag field and a
MultipleChoice(reader, author, reviewer) field are indistinguishable from a
plain String one. HUMAN_TITLE is absent. The PROPERTIES block is absent
entirely, so IS_COMPOSITE, PREFIX and VIEW_STYLE do not appear. Relations carry
TYPE and ROLE but not REVERSE_ROLE.

That rules the JSON export out as the oracle for the grammar milestone's
acceptance item 4, which compares the model strictdoc builds from an emitted
.sgra against the model it builds from the committed one: two grammars differing
in any of the four would compare equal. The comparison has to run in process
against the parsed document model, not over exported JSON. It also bounds what
the sdoc-cli milestone can learn about a grammar from the export it already
depends on.
<<<
RATIONALE: >>>
Noted while checking that the foreign fixture actually exercised the surface it
claims to. The export accepted every feature and then reported almost none of
them back, which is exactly the shape that makes a round-trip check pass without
having checked anything.
<<<

[MECHANISM]
UID: MECH-SGRA-SCANNED-PROJECT-WIDE
TITLE: A whole-project export reads every .sgra under the root, referenced or not
DEPTH: sketch
AUTHORED_BY: llm
STATEMENT: >>>
strictdoc export . reads every file with an .sgra extension anywhere beneath the
project root, whether or not a document imports it. A grammar file that fails to
parse therefore fails the whole export, from wherever it sits in the tree.

Measured on 0.28.3 while committing the negative fixture corpus for the grammar
milestone: six deliberately invalid grammars under
packages/strictdoc-grammar/fixtures/negative/ took the repository-wide export
from exit 0 to exit 1, on a file nothing referenced. They now carry an
.sgra.invalid suffix so the scan skips them, which works but encodes the
constraint in a filename rather than in configuration.

exclude_doc_paths in strictdoc_config.py is the configured answer and already
carries two globs for the same class of problem with .md files. Whether the
fixture suffix or a third glob is the right shape is undecided; the glob keeps
fixtures under their natural extension, the suffix keeps the config from
listing every directory that might hold one.
<<<
RATIONALE: >>>
The failure is remote from its cause -- the export names the fixture, but
nothing connects "a file I added under packages/" to "the command that reads the
design graph". A session that adds an invalid grammar anywhere and then sees the
graph command break has no reason to look in packages/ for it.
<<<
NOTES: >>>
A second producer of .sgra files under the root arrived 2026-08-27: the
ai.strictdoc module's generate:sgra task writes every declared grammar into the
working tree. It MITIGATES this node rather than resolving it. The task writes
through a temporary file carrying a LEADING DOT, so a crashed run cannot strand
a visible `grammar.sgra.XXXXXX` beside the real one for a whole-project export
to pick up as another grammar.

That is the constraint encoded in a filename for a second time, next to the
fixtures' .sgra.invalid suffix. Two encodings of one rule, neither of them in
strictdoc_config.py, is the argument for settling the exclude_doc_paths question
rather than an argument against it.
<<<

[MECHANISM]
UID: MECH-MULTIPLECHOICE-QUOTING-ASYMMETRY
TITLE: SingleChoice and MultipleChoice options are quoted by different rules on read and on write
DEPTH: sketch
AUTHORED_BY: llm
STATEMENT: >>>
Measured on 0.28.3 while writing the .sgra emitter. StrictDoc's reader and
writer treat SingleChoice and MultipleChoice options differently, and only
SingleChoice is self-consistent.

GrammarElementFieldSingleChoice strips a surrounding double quote from every
option at construction, and get_unprocessed_options re-adds it on write for any
option containing a parenthesis. GrammarElementFieldMultipleChoice does
neither: the model keeps whatever quoting the file carried, and the writer joins
options verbatim.

Two consequences. A MultipleChoice option holding a parenthesis, built
programmatically without quotes, is written to a file that does not parse --
verified, it fails with a TextXSyntaxError expecting a separator or a closing
parenthesis at the inner one. And a correctly quoted one round-trips
byte-stable but carries the literal quote characters inside the model's option
string, so a node's field value has to include them to match.

The emitter quotes parenthesized options for both kinds, because that is the
only spelling the grammar accepts. The residual asymmetry is in the model value
and is upstream's.
<<<
RATIONALE: >>>
Noticed because the emitter's quoting rule was specified as what strictdoc's own
writer does, and the writer does two different things depending on the field
kind. Worth knowing before any consumer compares an option vocabulary against a
field value, and before anyone treats strictdoc's writer as the byte-identity
oracle for a grammar that uses MultipleChoice.
<<<

[MECHANISM]
UID: MECH-DUPLICATE-ELEMENT-TAG-SILENT
TITLE: Duplicate element TAG is a third silent grammar collision
DEPTH: sketch
AUTHORED_BY: llm
STATEMENT: >>>
Measured on 0.28.3. Two grammar elements sharing a TAG parse clean and export
exit 0. DocumentGrammar registers each element with an assignment into
elements_by_type keyed on the tag, so the lookup keeps the LAST while
grammar.elements still holds both. Verified directly: a two-element grammar with
both elements tagged X reports elements X and X, registered_elements holding the
single name X, and elements_by_type for X carrying the SECOND element's fields.

That is the same class as the duplicate field title and duplicate relation role
cases the implementation brief records, and the same direction as the field one.
The brief says those two are the only checks that belong at Nix evaluation; that
count is one short.

packages/strictdoc-grammar/lib/emit.nix already guards it in its whole-file
renderer alongside the other two. The open item is the brief's line, and the
prior question of whether such checks belong to the emitter at all or to the
type surface.
<<<
RATIONALE: >>>
Found while proving the emitter, by asking whether the two documented collisions
were the whole set rather than by happening to hit one.
<<<

[MECHANISM]
UID: MECH-NIX-REGEX-DIALECT-GAP
TITLE: Nix's regex engine cannot express the dialect StrictDoc's grammar is written in
DEPTH: sketch
AUTHORED_BY: llm
STATEMENT: >>>
Measured on 0.28.3 while writing the faithful extractor. builtins.match is
POSIX ERE. It rejects, outright and at match time rather than at declaration
time, three constructs the .sgra grammar uses: negative lookahead, the \S class
shorthand, and backreferences. Three of the nineteen reachable rules carry one:
FieldName is (?!^UID)(?!^RELATIONS)..., SingleLineString is (?!>>>\r?\n)\S...,
and ChoiceOption is (["])[^,]+\1|[^,()"]+.

So "faithful means the exact regex" and "the type is checkable" cannot both
hold. lib/faithful.nix therefore carries two spellings per pattern -- source,
upstream's verbatim, and ere, a mechanical rewrite -- plus the named rewrites
that got from one to the other and any deny prefixes a hoisted lookahead
became. Every rewrite is exact rather than widening: a lookahead becomes an
explicit prefix rejection, and a construct no named rewrite claims raises.

The open item is that nothing re-validates ere against source. A rewrite that
silently widened would pass every check in this milestone, because the only
oracle is that the ERE compiles at all.
<<<
RATIONALE: >>>
Worth knowing before anyone reads the surface as carrying upstream's patterns
verbatim, and before the normalizer treats ere as the authority. source is the
authority; ere is a derived artifact of a translation with no test behind it.
<<<

[MECHANISM]
UID: MECH-TEXTX-ASGN-ATTR-NAME
TITLE: The peg assignment node carries its attribute name, and positional correlation is wrong
DEPTH: sketch
AUTHORED_BY: llm
STATEMENT: >>>
Measured on textx as pinned by 0.28.3. A synthetic __asgn_plain /
__asgn_oneormore / __asgn_zeroormore node carries _attr_name and _exp_str, both
the attribute's name. That is the correct way to pair a peg assignment with the
metamodel attribute it fills.

The obvious alternative -- pairing them positionally, since _tx_attrs preserves
declaration order -- is wrong, and wrong in exactly one place, which is the
worst shape for a bug like this. GrammarElementFieldSingleChoice and
GrammarElementFieldMultipleChoice each assign options TWICE, as
(options = ChoiceOption) (options *= ChoiceOptionXs), so they have five
assignment nodes against four attributes and every attribute after the third
shifts by one. Every other reachable rule correlates positionally just fine.
<<<
RATIONALE: >>>
Recorded because a positional walk passes on eighteen of nineteen rules and
then mislabels REQUIRED as options on the two choice-field rules, which is a
plausible surface that type-checks and is silently wrong.
<<<

[MECHANISM]
UID: MECH-PEG-REACHABILITY-COUNT
TITLE: Nineteen rules are reachable from DocumentGrammarWrapper, not twenty-five
DEPTH: sketch
AUTHORED_BY: llm
STATEMENT: >>>
Measured on 0.28.3. Walking rule references out of the arpeggio parser tree,
unioned with _tx_inh_by for the two abstract rules, closes at NINETEEN rules
from DocumentGrammarWrapper: BooleanChoice, ChoiceOption, ChoiceOptionXs,
DocumentGrammar, DocumentGrammarWrapper, FieldName, GrammarElement,
GrammarElementField and its four concrete kinds, GrammarElementRelation and its
three concrete kinds, RequirementType, ReservedKeyword, SingleLineString.

The implementation brief says 25 of 43. The difference is the access path, not
the grammar: _tx_attrs reports an attribute's declared class, and for a value
that is an inline regex textx declares it STRING, which drags textx's
synthesized base types (STRING, ID, BOOL, INT, FLOAT, STRICTFLOAT, NUMBER,
OBJECT, BASETYPE) into a metamodel-side walk. None of them appears in the peg,
and none of them constrains anything a .sgra file can say.
<<<
RATIONALE: >>>
Both numbers are right about their own walk. Recorded so a later session
checking the surface for completeness against the brief's 25 does not go
looking for six missing rules that are not rules of this grammar.
<<<

[MECHANISM]
UID: MECH-EXTRACT-WRAPPER-NO-FORMATTER
TITLE: The extraction wrapper carries no Nix formatter, so generation is only idempotent by accident
DEPTH: sketch
AUTHORED_BY: llm
STATEMENT: >>>
overlays/dev-tools/strictdoc-grammar-extract.nix puts strictdoc's dependency
closure and ast-grep on the wrapper's PATH. It does not put alejandra there.

Generated Nix has to come out already formatted, or treefmt rewrites it and the
next --check reads that rewrite as drift. extract.py therefore shells out to
alejandra and warns when it is missing. In a devenv shell it resolves from the
ambient PATH, which is why generation is currently idempotent -- verified,
treefmt reports 0 changed and --check exits 0 -- but that is the operator's
profile doing the work, not the package.

Two ways to close it: add alejandra to the wrapper's --suffix PATH, or have the
generator emit alejandra's canonical form directly. The first is one line and
makes the warning unreachable.
<<<
RATIONALE: >>>
Noticed because the warning path is the one that runs in CI, where the wrapper
is the whole environment. A CI regeneration would silently produce a file that
the repository's own formatter immediately changes.
<<<
NOTES: >>>
The FILE moved 2026-08-27 and the finding did not. The wrapper is now
packages/strictdoc-grammar/lib/mkExtract.nix, the overlay having been deleted
outright (MECH-GRAMMAR-EXTRACT-SOURCE-BOUNDARY); alejandra is still deliberately
absent from it, and the header now says so in as many words rather than leaving
it to be noticed. The workaround is still per-caller:
checks/strictdoc-grammar-surface-current.nix names alejandra in
nativeBuildInputs. Neither of the two ways to close it has been taken. Read
together with MECH-FORMAT-NIX-DOWNGRADES-A-MISSING-FORMATTER, the same defect
seen from the generator's side.
<<<

[MECHANISM]
UID: MECH-LIST-SEPARATOR-SUPPRESSED
TITLE: A separated list's separator does not survive into the faithful surface
DEPTH: sketch
AUTHORED_BY: llm
STATEMENT: >>>
Measured on 0.28.3. The choice-option list is spelled

  '(' ((options = ChoiceOption) (options *= ChoiceOptionXs)) ')'

and ChoiceOptionXs is the separator-carrying rule:

  ChoiceOptionXs[noskipws]: /, /- ChoiceOption

The `-` suffix is arpeggio's suppression marker, and the extracted production
for ChoiceOptionXs carries only the rule reference: the /, / match is gone.

So the SHAPE of a separated list is derivable from the surface -- one mandatory
assignment then a zeroOrMore assignment to the same option -- and the
normalizer classifies it from exactly that. The SEPARATOR is not. The ", " join
therefore lives in the encoder as knowledge rather than as a derivation, in
both lib/emit.nix and the `commaList` pair in extract/normalize.py.

Fix shape: teach extract.py to record suppressed matches as a `separator` on
the repetition item, and have the encoder read it.
<<<
RATIONALE: >>>
The whole point of generating the surface is that no vocabulary is hand-typed.
", " is currently a hand-typed constant in two files, and if upstream ever
changed the separator both would keep emitting the old one against a grammar
that no longer parses it.
<<<

[MECHANISM]
UID: MECH-DSL-SHAPE-DIVERGES-FROM-SURFACE
TITLE: The DSL and emitter value shape does not typecheck against the generated surface
DEPTH: sketch
AUTHORED_BY: llm
STATEMENT: >>>
Two incompatible field shapes are live at once in packages/strictdoc-grammar.

The generated surface follows textx, which repeats TITLE inside every
alternative, so a field is the union itself:

  {singleChoice = {title = "STATUS"; options = ["Draft"]; required = true;};}

lib/dsl.nix and lib/emit.nix follow the implementation brief's "shape, as
designed", which hoists the title out and names the union `kind`, and which
spells the vocabulary `choices`:

  {title = "STATUS"; kind.singleChoice = {choices = ["Draft"];};}

Both evaluate. They do not typecheck against each other: values built with the
DSL are never checked by types.GrammarElementField, so the brief's acceptance
item 3 -- "the DSL evaluates and cannot weaken the types" -- is not currently
demonstrable, and item 4's round trip runs entirely on the emitter's own shape.

Fix shape: one of the two moves. Either the emitter and DSL adopt the generated
shape, or normalize.py grows a converter pair that rewrites the union into
title-plus-kind and encodes back -- which is exactly what a converter pair is
for, and would make the hoist a recorded decision rather than a divergence.

RESOLVED by the integration step of the same milestone, by the FIRST move.
lib/dsl.nix and lib/emit.nix now speak the generated shape, `kind` is gone, and
lib/check.nix runs every value through types.DocumentGrammar before emit sees
it. The vocabulary is spelled `choices` on both sides because the extractor
renames it: `options` is unusable as a submodule CONFIG key -- the module system
reads it as an option declaration. Left in place rather than deleted because
removing a backlog node is the operator's call.
<<<
RATIONALE: >>>
Noticed while checking that emit.nix consumes normalized.encoders: it does, but
it reads `body.choices` off a value the normalized types would reject. Two
shapes that both work in isolation are the kind of thing that only surfaces
when someone finally wires the check that compares them.
<<<

[MECHANISM]
UID: MECH-CHOICE-ENCODER-PAIR-SPLIT
TITLE: The choice-option converter pair is split across two files with nothing checking they agree
DEPTH: sketch
AUTHORED_BY: llm
STATEMENT: >>>
ChoiceOption is now the one converter whose two halves live in different files.
The type rewrite is `decodedOption` in extract/normalize.py, which turns the
faithful token pattern into the DECODED option value; the encode half is
`choiceOption` in lib/emit.nix, which puts the quotes back.

The split is deliberate -- when to quote is decided by
GrammarElementFieldSingleChoice.get_unprocessed_options, which lives in
strictdoc's WRITER and not in the grammar the surface is derived from, so
normalize.py has no business deriving it. Every other pair ships both halves
from normalize.py, and emit.nix merges `defaultEncoders // normalized.encoders`
so a name shipped there wins.

The cost is that nothing checks the two halves agree. If upstream widened the
unquoted branch, or started quoting on a different condition, the type would
accept a value the encoder spells in a way the grammar no longer parses -- and
the only thing that would notice is the round-trip fixture happening to contain
such an option.

Fix shape: have normalize.py record the DECODE half's inverse as an assertion
the check task can run, or move the quoting rule in by extracting it from the
writer the same way the grammar is extracted from the builder.
<<<
RATIONALE: >>>
Found by rendering fixtures/foreign.nix: `MIT (Expat)` failed the faithful
ChoiceOption pattern, because the faithful type describes the TOKEN as written
(quoted, for a parenthesised option) while the value in Nix is the option
itself. Adding the decode converter fixed it, and made the pair's split
explicit for the first time.
<<<

[MECHANISM]
UID: MECH-LINE-ANCHORED-DENIAL-UNENFORCED
TITLE: FieldName's anchored denials are decided from a register, not from the grammar
DEPTH: sketch
AUTHORED_BY: llm
STATEMENT: >>>
The split itself is now decided per word rather than per anchor, and the rule
is in decompose.py: run each denied word against the SIBLING ALTERNATIVES of
the rule that denies it, enforce the ones that are an alternative of nothing,
and record the rest. `sibling_alternatives` computes that set off the
production tree, so the decision is the grammar's wherever the grammar shows
it, and an anchored denial that is neither computable nor registered is a hard
error.

What is left is that FieldName's two answers are REGISTERED, in
decompose.LINE_ANCHORED_DENIALS, rather than derived. The rule that gives its
lookaheads their purpose is SDocNodeField, which lives in the DOCUMENT grammar
and is not in the recipe this surface walks -- the .sgra grammar only ever
enters FieldName after the literal '  - TITLE: ', which is a position no choice
discriminates. So the register carries UID (an alternative of SDocNodeField, a
backtracking guard, unenforced) and RELATIONS (an alternative of nothing, a
reservation, enforced), each with its reason.

A register entry is a human decision about a rule nobody is reading, and it
cannot notice upstream moving a word from one bucket to the other. Fix shape:
walk the document grammar too, at least far enough to read the alternatives at
each anchored rule's entry positions, and let the same discriminator answer
without a register. The discriminator is already exercised against a synthetic
SDocNodeField-shaped recipe, so what is missing is the input, not the rule.
<<<
RATIONALE: >>>
The first spelling of this rewrite was `strip-start-anchor`, which dropped the
caret and enforced the rest, and it produced a FieldName type that rejected UID
-- caught only when values.nix was first checked against the surface. Getting
it right in one direction should not be mistaken for having a check.
<<<
NOTES: >>>
RESOLVED 2026-08-26 with the operator, and the resting state was wrong. The two
denied words are not the same kind of thing, and a rule read straight off the
grammar separates them: run each denied word against the SIBLING ALTERNATIVES
of the rule that denies it. A word that appears as an alternative is a
backtracking guard. A word that appears as none is a real reservation.

UID appears as its own literal alternative in SDocNodeField, so denying it as a
value would be wrong -- a field named UID is legal and this repository declares
one five times.

RELATIONS appears as no alternative, and MEASURED it is a genuine defect: a
grammar declaring a field titled RELATIONS exports clean with exit 0, and a
document that USES that field fails to parse, because the parser reaches
RELATIONS: expecting the relations block header. So strictdoc will accept a
grammar that generates documents nobody can read, and says nothing at the layer
where the mistake was made. That is precisely what a type here can catch.

Enforcing it needs no regex and no new machinery. patternType already carries an
addCheck branch for its enforced deny list, and a denial lifted out of a pattern
is a list-membership test rather than a lookahead -- which is what makes it
expressible at all, since POSIX extended regex has no lookaheads. Verified that
addCheck fires on a scalar string type: DEPTH and UID accepted, RELATIONS and a
lowercase name rejected.

The earlier reasoning here was wrong twice over -- that the machinery did not
exist, and that a lookahead's absence from the regex dialect meant the rule
could not be enforced at all.

IMPLEMENTED 2026-08-27, together with moving the whole decomposition out of the
faithful surface. FieldName now carries deny = ["RELATIONS"] and
denyAtLineStart = ["UID"], and the type rejects a field titled RELATIONS,
accepts one titled UID, and still rejects a lowercase title. The rendered
grammar is byte-identical to docs/sdoc/grammar.sgra, which declares UID five
times, so the accept arm is not a bare assertion. What this node still names is
the register, not the enforcement.

DEPTH STAYS sketch, which is not drift against the paragraph above. What landed
is the enforcement; what this node is TITLED for -- deriving FieldName's two
answers from the document grammar instead of registering them -- is unbuilt and
has no design yet. Raising DEPTH here would report the residual as done.
<<<

[MECHANISM]
UID: MECH-ENFORCED-DENIAL-IS-A-PREFIX
TITLE: An enforced denial rejects every word starting with it, and only the exact word was measured
DEPTH: sketch
AUTHORED_BY: llm
STATEMENT: >>>
patternType's addCheck branch rejects a value whose PREFIX is a denied word --
`builtins.match "(${d}).*"` -- so enforcing RELATIONS also rejects a field
titled RELATIONSHIP or RELATIONS_2.

That is the faithful transcription. `(?!^RELATIONS)` denies a prefix too: the
caret constrains where the lookahead applies, not how much of the input it
covers, so upstream rejects exactly the same set at a line start. RequirementType
already relies on the same reading, which is why DOCUMENT_FROM_FILE is reserved
along with DOCUMENT.

What was MEASURED is narrower than what is enforced. The defect behind the
enforcement was measured on the exact word RELATIONS: a grammar declaring that
field exports clean and its documents then fail to parse. Nobody has run the
same experiment on RELATIONSHIP, so it is possible -- not likely, but untested
-- that the document grammar recovers on a longer word and the type is stricter
than the parser.

Fix shape: render a grammar declaring a RELATIONSHIP field, export it, and read
a document that uses it. If it parses, the two denial kinds want different
enforcement -- a prefix test for the reserved-keyword kind and an equality test
for this one -- and patternType needs the second branch.
<<<
RATIONALE: >>>
Noticed while wiring the enforcement: `deny` was reused because patternType
already carried the branch, and reuse imported prefix semantics along with it.
That is the right default, but it widens a rejection past the measurement that
justified it, and the widening is invisible in the generated file.
<<<

[MECHANISM]
UID: MECH-GRAMMAR-SGRA-NOT-GENERATED
TITLE: docs/sdoc/grammar.sgra is generated from values.nix and CI-gated
DEPTH: implemented
AUTHORED_BY: llm
STATEMENT: >>>
packages/strictdoc-grammar/values.nix renders docs/sdoc/grammar.sgra byte for
byte, and the semantic comparison agrees, but nothing writes that file. The
generation task deliberately stops at the two generated surfaces, and
check:sdoc-grammar renders to a temporary file and diffs.

So there are two sources for one artefact. Editing grammar.sgra by hand is
still possible and reddens only a task nobody has to run; editing values.nix
without running it changes nothing. Neither drift is caught anywhere near where
it happens, and neither is caught in CI at all -- both tasks depend on
interactive-only packages.

Fix shape: the operator decides whether grammar.sgra becomes generated. If yes,
generate:sdoc-grammar writes it and the drift check moves into `nix flake
check`, which needs the strictdoc closure available to a check derivation --
checks/strictdoc-fp-check.nix already pulls it via nativeBuildInputs, so the
precedent exists.
<<<
RATIONALE: >>>
Left as a deliberate stop rather than an oversight: making a hand-maintained
contract file generated changes who owns it, and this milestone was told not to
edit that file at all. Recorded so the half-wired state is legible as a
decision rather than read as a missing task.
<<<
NOTES: >>>
RULED by the operator 2026-08-26: yes, generate it. In this repository every
sdoc grammar is generated, by way of the devenv module in
MECH-STRICTDOC-DEVENV-MODULE. That is a local convention and is explicitly NOT
imposed on anyone consuming the published surface -- a consumer may use the
module, call the library directly, or hand-write the file.

Implemented 2026-08-27. ai.strictdoc.grammars.repo in devenv.nix names
docs/sdoc/grammar.sgra as its target, and the module's own generate:sgra task
writes it. The file it wrote is byte-identical to the one that was committed,
so the deliberate normalization commit acceptance item 5 allows for was not
needed.

Two things learned wiring it. The write CANNOT share an invocation with
generate:sdoc-grammar: `rendered` is an evaluation-time string and devenv fixes
every task's script before running any of them, so a chained write would emit
the grammar rendered from the surface that existed when the run began -- in
exactly the run that regenerated it. And the drift this node worried about is
already gated in CI rather than only by an interactive task:
checks/strictdoc-grammar-model-equal.nix renders values.nix inside `nix flake
check` and diffs it against the committed bytes, so a hand edit to either side
now reddens a required check.
<<<

[MECHANISM]
UID: MECH-MID-IS-PER-PARSE-RANDOM
TITLE: StrictDoc mints a fresh MID on every parse, so two reads of one file disagree
DEPTH: sketch
AUTHORED_BY: llm
STATEMENT: >>>
Measured on 0.28.3 while writing extract/compare.py. Every node StrictDoc
builds carries a `mid`, and for a .sgra it is generated fresh on each parse --
a .sgra has no syntax to declare one. Reading the SAME BYTES twice therefore
produces two models that disagree on every `mid` in the file.

Any structural comparison of two models has to skip it. Keeping it is not a
stricter comparison, it is one that can never pass, and because the difference
is per-parse rather than per-file it does not look like a bug in whatever
produced the second file.

The consequence beyond comparison: a MID is not an identity that survives a
re-read, so nothing may key on one across parses.
<<<
RATIONALE: >>>
The first run of compare.py against two byte-identical files reported them
different, with a mid mismatch on every node. Worth knowing before anything
else -- a diff tool, a cache key, a cross-file reference -- treats a MID as
stable.
<<<

[MECHANISM]
UID: MECH-EXPORT-FRAMES-VALIDATION-AS-PARSE-ERROR
TITLE: strictdoc export reports a semantic rejection as "could not parse file"
DEPTH: sketch
AUTHORED_BY: llm
STATEMENT: >>>
Measured on 0.28.3 while wiring checks/strictdoc-grammar-negative-fixtures.nix.
A grammar that violates an SDocValidator rule -- REVERSE_ROLE without ROLE,
SECTION not composite, TEXT composite -- is rejected during the step strictdoc
prints as `Build traceability graph`, well after `Reading SDOC` reports the
same file read successfully. The first line of the diagnostic is nevertheless:

  error: could not parse file: g.sgra.
  Semantic error: Grammar element 'NOTE' defines REVERSE_ROLE without ROLE ...

So the headline names the wrong layer, and the line that names the right one is
below it. Anything classifying a rejection by matching the error TEXT will read
every semantic failure as a parse failure -- and a fixture asserting "rejected
at the parse" would pass while proving nothing about the parser.

The layer is still distinguishable, just not from the message: a bare
SDocGrammarReader.read of the .sgra accepts all three, and only the whole-corpus
export rejects them. That is what the check discriminates on.
<<<
RATIONALE: >>>
Worth recording because the misleading half is the part a reader sees first, and
because it makes the obvious implementation of a layer assertion silently wrong
rather than loudly wrong.
<<<

[MECHANISM]
UID: MECH-GRAMMAR-CHECKS-ARE-IN-FLAKE-CHECK
TITLE: The five grammar gates are flake checks, so they are in the CI gate too
DEPTH: sketch
AUTHORED_BY: llm
STATEMENT: >>>
checks/strictdoc-grammar-{surface-current,surface-live,model-equal,
negative-fixtures,foreign-roundtrip}.nix are registered in flake.nix's `checks`
output, because that output is what makes `nix build .#checks.<system>.<name>`
addressable. There is no third state: `nix flake check` builds everything in
`checks`, so these now run in CI as well, on both x86_64-linux and
aarch64-darwin.

The cost is a closure, not a runtime: `pkgs.ai.devTools.strictdoc` was already
pulled in by strictdoc-fp-check and strictdoc-cycle-check, but the extraction
wrapper is new to CI, and so is alejandra as a check input. That wrapper is
packages/strictdoc-grammar/lib/mkExtract.nix, which puts ast_grep_py on
PYTHONPATH around upstream's own venv interpreter -- not the deleted
overlays/dev-tools/strictdoc-grammar-extract.nix, and not a python env carrying
a second copy of strictdoc's dependency closure.
Every one of the five builds in under a second once its inputs exist.

If the milestone's "wires no CI" is to hold literally, the five move out of
`checks` into a separate flake output and lose the addressable name. That is
the operator's call, not this session's. It was four when this node was
written; -surface-live.nix was added afterwards, in the same milestone, and the
count is the kind of thing that goes stale silently.
<<<
RATIONALE: >>>
Recorded because the milestone brief says CI wiring is not required, and this is
the one place where "buildable locally by name" and "not in CI" cannot both be
true. Better legible as a consequence than discovered from a CI bill.
<<<

[MECHANISM]
UID: MECH-FORMAT-NIX-DOWNGRADES-A-MISSING-FORMATTER
TITLE: emit_nix.format_nix warns on a missing alejandra, which makes --check lie
DEPTH: sketch
AUTHORED_BY: llm
STATEMENT: >>>
extract/emit_nix.py's format_nix() shells out to alejandra when it is on PATH
and otherwise prints a warning and returns the source unformatted. The
generator's own wrapper package deliberately carries only what extraction needs,
so alejandra is NOT on the PATH a bare `strictdoc-grammar-extract` sees.

Consequence: `extract.py --check` run without alejandra diffs UNFORMATTED output
against the committed (formatted) file and reports drift that does not exist.
It fails red rather than green, so nothing is silently accepted -- but the
failure names the wrong problem, and the diff it prints is pure formatting.
checks/strictdoc-grammar-surface-current.nix works around it by naming alejandra
in nativeBuildInputs.

Fix shape: make a missing formatter FATAL under --check while leaving it a
warning when writing, or put alejandra on the wrapper's PATH and drop the
conditional entirely.
<<<
RATIONALE: >>>
The warning is the right call for a write, where an unformatted file is fixed by
the next treefmt. It is the wrong call for a comparison, where the formatter is
part of what "current" means.
<<<

[MECHANISM]
UID: MECH-TREE-SITTER-CHOICE-OPTION-CANNOT-LEX-A-DOT
TITLE: The patched tree-sitter grammar cannot lex a dot in an unquoted choice option
DEPTH: sketch
AUTHORED_BY: llm
STATEMENT: >>>
overlays/generic/tree-sitter-strictdoc.patch now adds the QUOTED arm to
choice_option, which is the only way to write an option containing a
parenthesis and which costs ZERO regressions on strictdoc's own docs. The
UNQUOTED arm is still upstream's `[\w/-]+`, so an option containing a `.` --
`GPL-3.0-or-later`, any SPDX identifier with a version -- does not parse, even
though strictdoc itself accepts it (`(["])[^,]+\1|[^,()"]+`).

Widening the charset was measured three ways and every one lost, all on
strictdoc_04_release_notes.sdoc against a 9-error-node baseline:

  transcribing strictdoc's own classes  -> 89 nodes, 76795 -> 98406 error bytes
  upstream's charset plus a bare `.`    -> 89 nodes
  a dot only BETWEEN word runs          -> 108 nodes

The error BYTES rise with the node count, so this is a real loss of coverage,
not error-recovery reshaping. Cause: tree-sitter lexes by longest match over
every token valid in the current state -- and in an error-recovery state every
token is valid -- so a wider choice_option out-competes the narrow tokens
wherever recovery is running.

Fix shape: restrict WHERE the token can be lexed rather than widening WHAT it
matches -- an external scanner, or restructuring grammar_field_single_choice /
_multiple_choice so the option list is lexed in a state of its own. Belongs to
SLICE-SDOC-IN-SEMBLE, which owns the grammar patch.

Until then packages/strictdoc-grammar/fixtures/foreign.sgra carries
`GPL-3-only`, not `GPL-3.0-or-later`; the dot was incidental to what that
fixture exercises and its README says so.
<<<
RATIONALE: >>>
Found by checks/strictdoc-grammar-corpus.nix the moment foreign.sgra entered the
repository's own corpus -- the check did exactly its job. Recorded rather than
fixed because a charset is the wrong lever and the right one is a grammar
restructure in another slice.
<<<

[MECHANISM]
UID: MECH-CORPUS-CHECK-COUNTS-ERROR-NODES-NOT-SPAN
TITLE: The corpus check's no-regression arm counts ERROR nodes, which recovery reshapes
DEPTH: sketch
AUTHORED_BY: llm
STATEMENT: >>>
checks/strictdoc-grammar-corpus.nix gates a grammar change on the number of
ERROR/MISSING NODES per already-failing file. That number is a property of how
tree-sitter's error recovery segmented the unparsed text, not of how much text
went unparsed: one candidate patch took strictdoc_01_user_guide.sdoc from 42
nodes to 19 while its error BYTES fell 1921 -> 501 (a genuine improvement), and
another took strictdoc_04_release_notes.sdoc from 9 nodes to 89 with error bytes
rising 76795 -> 98406 (a genuine loss). Both directions happened to agree here,
so the check's verdict was right -- but only by luck, since a change that merely
fragments one big ERROR into many reads as a large regression.

Fix shape: report both, and gate on the byte span. The node count stays useful
as a diagnostic.
<<<
RATIONALE: >>>
Noticed while iterating on the choice_option widening above, where the node
count was the only signal available and had to be cross-checked by hand against
the spans before the verdict could be trusted.
<<<

[MECHANISM]
UID: MECH-GRAMMAR-GATES-ARE-WRITTEN-TWICE
TITLE: dev/tasks/check.nix restates the flake checks instead of running them
DEPTH: sketch
AUTHORED_BY: llm
STATEMENT: >>>
`check:sdoc-grammar` and checks/strictdoc-grammar-*.nix implement the same
acceptance list twice, in bash and in Nix, against the same fixtures. They agree
today. Nothing makes them agree tomorrow: the flake checks read committed bytes
through the flake's `self` while the task reads the working tree, and only the
flake side reads the layer expectation out of fixtures/README.md, so the task's
negative arm accepts a fixture failing for the wrong reason.

Acceptance item 3 is already handled the other way -- the task shells out to
`nix build .#checks.<system>.strictdoc-grammar-surface-live` rather than
restating its case table -- and that is the shape the rest should converge on:
the task becomes a working-tree render plus a deferral, and the assertions live
in one place.
<<<
RATIONALE: >>>
Written when item 3 was added and the choice had to be made once. Deferring is
cheap for a new arm and a rewrite for the existing five, so the existing five
were left alone and the divergence recorded instead of half-fixed.
<<<
NOTES: >>>
The operator asked for a position rather than a question, 2026-08-26. Position:
the flake check is the gate and the devenv task should defer to it, which one of
the six arms already does. The duplication is therefore a defect rather than a
design.

Held rather than acted on, because the boundary it depends on is not written
down anywhere -- see MECH-CHECK-SYSTEM-BOUNDARY, which is the repo-wide version
and interacts with the standing intention to move checks into packages/.
<<<

[MECHANISM]
UID: MECH-DEFAULT-EXPORT-IS-RED-ON-RST
TITLE: The default export format fails on this corpus, so only --formats=json is ever green
DEPTH: sketch
AUTHORED_BY: llm
STATEMENT: >>>
`strictdoc export . --output-dir <dir>` with no `--formats` exits 1 on this
corpus, and always has. StrictDoc renders every node field through docutils on
the HTML path, and SLICE-SDOC-IN-SEMBLE's STATEMENT carries the bare glob
`*.sdoc`, which RST reads as an inline emphasis start-string with no end-string:
"problems when converting RST to HTML", raised from
rst_to_html_fragment_writer.py:231. Measured against strictdoc 0.28.3 on
2026-08-26. The prose predates this plan's tooling work.

Every documented loop in this repository passes `--formats=json` -- the sdoc
skill, docs/sdoc/README.md, the recipe in dev/scripts/fp-check.py and
cycle-check.py, checks/strictdoc-fp-check.nix and checks/strictdoc-cycle-check.nix
-- so the RST writer never runs and the breakage is invisible. Nothing checks
this corpus against the renderer a person would read it in.

The fix at authoring time is one character, and the rule is not the one it looks
like. MEASURED by driving docutils directly: a glob inside a single backtick is
CLEAN, and so is one inside double backticks, while a bare glob warns whether it
appears once or twice on a line -- an asterisk that opens emphasis needs a
closing asterisk that ENDS a word, and a glob never supplies one. So a pair of
globs on one line is not a matched pair; it is two unterminated openings.

Three bare sites exist today: 01-tooling.sdoc:195, 01-tooling.sdoc:208, and the
unquoted `checks/strictdoc-grammar-*.nix` inside
MECH-GRAMMAR-GATES-ARE-WRITTEN-TWICE, which this milestone wrote -- all three
confirmed to warn, by a session with no way to notice. The export aborts at the
first, so the count comes from probing docutils rather than from the export.

Fix shape: either escape globs at authoring time and put an HTML export in the
gate, or record that HTML is not a supported view of this corpus and make the
JSON-only loop explicit rather than incidental. Pinning formats per
MECH-SDOC-LEAN-FORMATS would settle it by removing the HTML writer -- note that
node's separate false green, where `--formats=html` then exits 0 having written
nothing.
<<<
RATIONALE: >>>
Found by the landing step running the milestone's validation loop literally as
worded -- "a clean export to a temp dir" -- rather than as the repository's own
scripts spell it. The two differ, and only one of them is green.
<<<
NOTES: >>>
RULED by the operator 2026-08-26: tech debt against this plan, LOW priority, may
sit unfixed for several milestones. Found during milestone one, which is where
it should be referenced back to.

The requirement it implies is separate and is tracked as
MECH-HTML-RENDER-MUST-PASS: whatever the fix, either repair the prose or make it
error loudly, but the operator does not want this to become a blocker on work
that has nothing to do with HTML.
<<<

[MECHANISM]
UID: MECH-UPSTREAM-GRAMMAR-CASES
TITLE: Borrow upstream's grammar test cases as fixtures rather than extracting them
DEPTH: sketch
AUTHORED_BY: llm
STATEMENT: >>>
The strictdoc package ships no .sgra files at all, and upstream's grammar test
data is multiline Python strings or objects built straight from constructors,
so there is no corpus sitting on disk to point a tool at. Building extraction
machinery for it would cost more than it returns.

Hand-convert a selection of their unit-test grammars into fixtures beside ours
instead. The value is edge cases nobody here would think to write, not
coverage: their tests were written against the parser by the people who wrote
it. Source is their tests/unit tree, the grammar-element tests specifically.
<<<
RATIONALE: >>>
Our fixtures test what we thought of. Theirs test what broke. The two sets
overlap less than either author would guess, and the conversion is a morning's
reading rather than a tool to maintain.
<<<

[MECHANISM]
UID: MECH-GRAMMAR-ARBITRARY-GENERATOR
TITLE: Derive a value generator from the grammar surface rather than writing one
DEPTH: sketch
AUTHORED_BY: llm
STATEMENT: >>>
Property testing for the grammar surface, deliberately deferred past milestone
one. The shape worth building is a generator derived from the same model the
surface is, the way a schema library derives one, so the generator and the type
cannot drift apart.

Point it at the ROUND TRIP -- generate a valid grammar, emit it, parse it with
strictdoc, compare -- not at whether the type accepts what the generator made.
The second proves almost nothing, because the generator was written from the
type.

Viable: lib.mod exists and builtins.fromTOML parses hexadecimal, so a seeded
generator in pure Nix is available if that is where it should live.
<<<
RATIONALE: >>>
The byte-identity gate covers one grammar. A round trip over generated ones
covers the shapes nobody wrote a fixture for, which is where an emitter that
handles our five node types and nothing else would still look correct.
<<<

[MECHANISM]
UID: MECH-MULTILINE-FIELD-RULES
TITLE: Which fields may carry block values belongs to the writing tool
DEPTH: sketch
AUTHORED_BY: llm
STATEMENT: >>>
A field's value is written either inline or as a block delimited by the
triple-angle markers, and strictdoc decides which from three things at once:
reserved single-line names are never blocks; otherwise position decides, with
everything after TITLE or STATEMENT being a block; and non-string types are
never blocks.

That is document-writing behaviour, not grammar declaration, so it belongs to
the milestone that makes a tool the only writer of sdoc files rather than to
the grammar surface. Recorded here explicitly UNSETTLED at the operator's
instruction, to be picked up there rather than rediscovered.
<<<
RATIONALE: >>>
It surfaced during the grammar milestone and was nearly settled in the wrong
place. A rule about how values are written cannot be enforced by a surface that
only declares what fields exist.
<<<

[MECHANISM]
UID: MECH-RESERVED-FIELD-DECLARATION-LIES
TITLE: A reserved field name can be declared with a type that is then ignored
DEPTH: sketch
AUTHORED_BY: llm
STATEMENT: >>>
Declaring UID as a choice type parses clean, and the document tokenizer then
ignores the declared type entirely, matching UID with its own hardcoded
expression. The declaration is a statement the grammar accepts and nothing
honours. The same holds for MID.

The operator's call was that this is not worth modelling in the Nix layer: the
reserved names are ones we depend on rather than ones to ban, and the surface
would be asserting a rule about a handful of names to catch a mistake nobody
has made. Recorded so that it reads as a decision rather than an oversight, and
so a later session does not spend the afternoon rediscovering it.
<<<
RATIONALE: >>>
Five of this repository's ten field names are reserved, so the behaviour is not
exotic. The reason to leave it alone is proportion, not ignorance of it.
<<<

[MECHANISM]
UID: MECH-DIRTY-EDGE-ON-OPTION-CHANGE
TITLE: A node whose inputs changed should go dirty rather than quietly stale
DEPTH: sketch
AUTHORED_BY: llm
STATEMENT: >>>
The operator's, and it belongs with the behaviour model rather than the grammar
surface. Once file relations are settled, a change to what a node depends on
should mark that node DIRTY -- visibly needing reconciliation -- rather than
leaving it silently stale, with a model filling the gap afterwards.

The fingerprint machinery already does this for node-to-node contracts. What it
does not cover is a relation pointing at a file, which today resolves to a path
that nothing checks for existence, let alone for change. Scope this where the
behaviour model lands.
<<<
RATIONALE: >>>
This is the point of the dirty-edge idea in the operator's semantics rather
than an incidental feature: staleness that announces itself is the difference
between a graph that decays and one that asks to be repaired.
<<<

[MECHANISM]
UID: MECH-HTML-RENDER-MUST-PASS
TITLE: Rendering to HTML should be a requirement, with a check that is not a full render
DEPTH: sketch
AUTHORED_BY: llm
STATEMENT: >>>
Make it a requirement that this corpus renders to HTML, and gate it. The
operator expects to use strictdoc's own site occasionally until their viewer
exists, so a corpus that only survives the JSON path is not good enough even
though JSON is the interface everything else uses.

The gate does not have to be a full render. Two shapes, and the second is
preferred: a light checker for the shapes known to break, or invoke the actual
parser strictdoc uses on each field and fail on its diagnostics. The second
avoids maintaining a corpus of known failures that will always lag what the
renderer actually rejects.

Matters more once a tool is the only writer of these documents, since that tool
is where the check belongs -- rejecting the prose at authoring time rather than
discovering it at export.
<<<
RATIONALE: >>>
MECH-DEFAULT-EXPORT-IS-RED-ON-RST is the instance; this is the rule that would
have caught it. A format nobody exercises decays silently, and this one decayed
without a single failing check.
<<<

[MECHANISM]
UID: MECH-OVERLAY-WRAPPING-BELONGS-IN-MODULES
TITLE: Move package wrapping out of overlays and into modules, repo-wide
DEPTH: sketch
AUTHORED_BY: llm
STATEMENT: >>>
Repo-wide, not attached to any milestone. An overlay should be the faithful
conversion of an upstream package and nothing more; wrapping -- environment,
flags, configuration -- belongs in the module that consumes it. That is the
operator's convention and it is not currently applied consistently:
overlays/kiro-cli.nix does its wrapping in the overlay, which is why it read as
the example to follow.

Sweep the overlays, list what wraps rather than converts, and move each into its
module. The operator wants to inspect that list rather than have an agent decide
edge cases against a stated invariant, so this is HITL at the point of sweeping,
not a mechanical migration.

One open question to answer first, because it changes the shape: if the devenv
module and the home-manager module wrap identically, does that build two
derivations, and can they share one?
<<<
RATIONALE: >>>
Overlays that wrap are the reason a consumer cannot take the package plainly,
and the reason an agent reading the tree infers the wrong convention from the
nearest example. Both showed up during milestone one.
<<<

[MECHANISM]
UID: MECH-AGENTS-INFER-OVERLAY-CONVENTION-FROM-EXAMPLES
TITLE: Agents keep putting wrapping in overlays because the examples do
DEPTH: sketch
AUTHORED_BY: llm
STATEMENT: >>>
A behavioural defect rather than a code one. The convention is that an overlay
converts and a module wraps, and agents have repeatedly done the opposite --
most recently the strictdoc grammar extractor, which shipped a wrapped
environment in the overlay.

The cause is not a missing rule; it is that the nearest example teaches the
opposite. An agent looking for the pattern finds overlays/kiro-cli.nix doing its
wrapping in the overlay and copies it. A written instruction loses to a working
example every time.

Fix in the same pass as MECH-OVERLAY-WRAPPING-BELONGS-IN-MODULES -- once the
examples agree with the convention, the inference stops being wrong. State it in
the overlay fragment as well, but do not expect the prose alone to hold.
<<<
RATIONALE: >>>
Recorded because the operator noticed it as a pattern across sessions rather
than as one agent's mistake, and because the remedy is to change what the tree
teaches rather than to write the rule down more firmly.
<<<

[MECHANISM]
UID: MECH-STRICTDOC-DEVENV-MODULE
TITLE: A devenv module owns strictdoc's wrapping and its grammar generation
DEPTH: implemented
AUTHORED_BY: llm
STATEMENT: >>>
Add a devenv module, named for the tool rather than the milestone --
ai.strictdoc, not ai.strictdocGrammar. Home-manager is deliberately out of
scope for now.

Surface:
  ai.strictdoc.enable    -- installs and wraps it in the dev shell
  ai.strictdoc.package   -- override the package, accepted as unsafe since the
                            generated option surface is pinned to a version
  ai.strictdoc.grammars  -- the intended way to configure it, and the path by
                            which this repository's own grammar file is
                            generated

Generating the grammar through this module is this repository's convention, not
a constraint on anyone consuming the published surface: a consumer may use the
module, call the library directly, or hand-write the file.

Closes the wrapping half of MECH-GRAMMAR-EXTRACT-SOURCE-BOUNDARY and settles
MECH-GRAMMAR-SGRA-NOT-GENERATED.
<<<
RATIONALE: >>>
The overlay currently ships a wrapped environment because an invariant about
overlays not importing from packages was read as forbidding the layout rather
than as pointing at the wrong layer. The module is where the wrap was always
meant to live.
<<<
NOTES: >>>
Implemented 2026-08-27, all three options live in
packages/strictdoc-grammar/modules/devenv/default.nix. `enable` installs
strictdoc plus the extraction runner, `package` carries its own unsafe-override
warning, and `grammars` is a typed attrset whose `elements` is declared with
the NORMALIZED type -- so a consumer handing raw attrsets to the emitter, which
asserts nothing by itself, cannot get past the module.

`generate:sgra` is the task that writes, and it is defined HERE rather than in
dev/tasks/generate.nix so the module references no task it does not own and
stays importable by a project that has none. It deliberately carries no edge to
generate:sdoc-grammar -- see MECH-GRAMMAR-SGRA-NOT-GENERATED for why chaining
the two would write a stale grammar.
<<<

[MECHANISM]
UID: MECH-STRICTDOC-UPSTREAM-FLAKE
TITLE: Take strictdoc from upstream's own flake instead of our overlay
DEPTH: implemented
AUTHORED_BY: llm
STATEMENT: >>>
strictdoc ships a flake. Cut over to it and retire the overlay written as step
zero of this plan.

The operator has accepted the consequence: an upstream flake tracks main rather
than releases, which is a change from the release-tracking the overlay was built
for and is normal practice. Worth watching rather than worth avoiding.

Check on the way through whether the two dependency adjustments the overlay
carries -- the newer reqif and the relaxed pygments pin -- are still needed, and
whether cache-hit parity survives, since an upstream flake brings its own lock.
<<<
RATIONALE: >>>
The overlay existed because nobody had checked for a flake. Keeping a
first-party override alongside an upstream one is two things to maintain for
one package.
<<<
NOTES: >>>
Implemented 2026-08-27. overlays/dev-tools/strictdoc.nix re-exports
inputs.strictdoc.packages.<system>.default unchanged, on the same plain-attrset-
update contract as overlays/semble.nix, so pkgs.ai.devTools.strictdoc keeps its
attribute path and its store path is byte-identical to a direct build of the
upstream flake. No consumer that takes the package from that seam changed.

Both questions the statement asked, answered. The dependency adjustments are
DEAD, not merely unneeded: upstream's flake is a uv2nix set built from the
repository's own uv.lock, which pins every dependency to the artifact the
release was tested against, so nothing resolves reqif or pygments against a
nixpkgs pin any more. Cache-hit parity SURVIVES and now holds trivially -- the
derivation closes over upstream's locked nixpkgs, so no consumer pin can move
it -- and the row was kept because a row that passes structurally is still what
catches a later final-bound wrapper.

The main-tracking consequence did not bite. Main was byte-identical to release
0.28.3 when the input was added (same tarball narHash), it built clean, and the
binary reports 0.28.3. The pre-approved contingency of pinning refs/tags/<rel>
was not used.

Two things this cost, both logged rather than fixed here. The version assertion
is gone -- MECH-STRICTDOC-VERSION-SMOKE. And SLICE-STRICTDOC-OVERLAY's STATEMENT
now specifies a build that does not exist ("a thin override of the nixpkgs
derivation ... from a sidecar, with the two dependency adjustments"); only its
NOTES record the change. Whether that statement is rewritten or the slice is
closed and superseded is a contract question and so the operator's, not an
implementing session's. RULED 2026-08-27: rewritten in place, because
superseding is not expressible for a slice -- `Superseded_By` is declared only
on DECISION. That statement now describes the shipped shape, and the missing
transition is logged as MECH-SLICE-CANNOT-BE-SUPERSEDED.

One consumer DID have to change, and it is the one that never went through the
seam. overlays/dev-tools/strictdoc-grammar-extract.nix read the derivation's
internals: `.dependencies` (a nixpkgs list of derivations) and
$out/<sitePackages>. Upstream's package is mkApplication over a virtual
environment, so $out holds bin/strictdoc and nothing else, and `dependencies`
is a uv2nix name-to-extras ATTRSET -- the splice throws at eval rather than
mis-resolving. It now wraps the venv interpreter named by that script's shebang,
which is the only handle on the venv since it is not a flake output, with
ast_grep_py added to PYTHONPATH from ourPkgs. MEASURED: upstream 3.14.6 against
ourPkgs 3.14.7, ast_grep_py imports clean, and the grammar builder returns the
same 4adcdb05... grammar the implementation brief records. That splice is a
minor-version coupling and the package's existing installCheckPhase is what
makes a future divergence fail at build time.

Written before the wrapper moved: it left overlays/ entirely later the same day
and is packages/strictdoc-grammar/lib/mkExtract.nix, so the path named above no
longer exists and its ourPkgs is now the consumer's pkgs. The splice, the
measurement and the coupling are unchanged -- see
MECH-GRAMMAR-EXTRACT-SOURCE-BOUNDARY.
<<<

[MECHANISM]
UID: MECH-CHECK-SYSTEM-BOUNDARY
TITLE: Decide what belongs in flake checks versus devenv tasks
DEPTH: sketch
AUTHORED_BY: llm
STATEMENT: >>>
Repo-wide, and a tangent from milestone one rather than part of it. Two check
systems exist -- the flake's checks output and devenv tasks -- and there is no
stated rule for which gets what. The grammar milestone ended up writing five of
its six acceptance arms in both.

A position to argue with rather than a conclusion: the flake output is the gate,
because it is what CI builds and what a consumer can run; devenv tasks are for
things a person triggers while working, and should defer to the flake check
rather than restate it. On that reading the duplication is simply wrong and the
devenv side should shell out, which one arm already does.

Interacts with the standing intention to move checks into packages/<package>
rather than leaving them in one large evaluation test.
<<<
RATIONALE: >>>
The operator did not know the repository had two check systems until this
milestone produced duplicate gates in both, which is itself the argument for
writing the boundary down.
<<<

[MECHANISM]
UID: MECH-CONTRACT-FIELDS-EDGE-TO-SEMANTIC-LAYER
TITLE: Contract-bearing fields are semantic, and their edge should move
DEPTH: sketch
AUTHORED_BY: llm
STATEMENT: >>>
SLICE-GRAMMAR-FROM-NIX still carries a Governed_By edge to
DEC-FP-FIELDS-CONFIGURABLE and a matching PARENT_FP entry, from when
contract-bearing fields were in its scope. They are not: which fields count as a
node's contract is special meaning laid over the grammar, so it belongs to the
semantic layer along with relation target sets and the lifecycle.

Move the edge to the milestone that delivers the semantic layer. The PARENT_FP
entry has to move with it and only the operator changes those.
<<<
RATIONALE: >>>
Left in place deliberately rather than overlooked: an agent editing PARENT_FP is
the failure this graph already recorded once.
<<<

[MECHANISM]
UID: MECH-CI-UP-TO-PAR-BEFORE-MERGE
TITLE: Bring CI up to par before this branch merges, not while proving it out
DEPTH: sketch
AUTHORED_BY: llm
STATEMENT: >>>
CI is required to merge, so this branch cannot land without it. The operator's
position for now is deliberately the other way round: additional CI tooling is
not required for the bulk of this experiment, because the point is to prove the
approach out before investing in machinery around it.

So: existing CI tooling is fine, and an agent that adds tooling without having
got that memo is also fine -- neither is worth reverting. What is needed is a
pass before merge that checks what actually gates the branch, rather than
discovering at restack time that the gates were never wired.

Do this when the long-lived branch is restacked into reviewable pull requests,
not before.
<<<
RATIONALE: >>>
Recorded because "CI is not required" and "CI is required to merge" are both
true at different times, and only writing the second one down keeps the first
from being read as permanent.
<<<

[MECHANISM]
UID: MECH-FAITHFUL-IS-NOT-A-CONSUMER-WORD
TITLE: Keep faithful out of the consumer glossary
DEPTH: sketch
AUTHORED_BY: llm
STATEMENT: >>>
Faithful describes a transformation methodology -- how the surface is derived
from strictdoc's own grammar, and the promise that no opinion was added on the
way. It is a contributor-side term. It may well exist as a contributor-side
grammar in its own right.

It should not appear in anything a consumer reads: not an option name, not an
attribute path, not documentation aimed at someone using the published surface.
A consumer does not care which of our layers a thing came from, and naming a
public entry point after the methodology asks them to learn our build process
before they can call a function.

Low priority. The operator may move this to a repository issue rather than
keeping it here.
<<<
RATIONALE: >>>
Raised when a lower-level emitter was about to be named faithful.emit. The name
was self-documenting only to someone who had read the three-layer design, which
is exactly the wrong audience test for a published interface.
<<<
NOTES: >>>
PARTLY CLOSED 2026-08-27, by the review round on the decomposition and the emit
split. `lib/default.nix` was still re-exporting `faithful`, so the barrel really
did publish the attribute path this node rules out; it now wires the layer as a
let-binding and exports `check`, `dsl`, `emit` and `normalized` only. Nothing
read it -- and nothing needs to, since `normalized` IS `faithful // { … }`, so
`normalized.productions` and `normalized.meta` are the same values under a name
that describes the layer rather than the methodology.

Still OPEN: the word remains in comments and in the two generated files' own
names (`lib/faithful.nix`), which is where a contributor meets it and is the
side of the line this node puts it on. Whether the FILE should be renamed too,
and whether this belongs in a repository issue rather than here, are the
operator's.
<<<

[MECHANISM]
UID: MECH-EMIT-LAYER-BOUNDARY
TITLE: Emit is the renderer composed with the type mapping, and they split cleanly
DEPTH: implemented
AUTHORED_BY: llm
STATEMENT: >>>
Settled with the operator 2026-08-26. Two jobs, one composition:

  the inner emitter -- takes values that are all strings, knows the FILE FORMAT,
    and does no encoding. A pure renderer.
  denormalize      -- knows the TYPE MAPPING: a Nix bool becomes the literal
    True or False, an enum member becomes its bare string, a list becomes a
    comma-space join.
  the outer emitter = the inner one composed with denormalize.

The normalized surface is deliberately a MIXTURE, and this is already how it is
built: a shape no converter upgraded stays as the extracted string, carried
inside normalized rather than pushed elsewhere. regexPreserved records that as
"unchanged" with a null encoder, and the current file has four upgraded sites
sitting beside five that stayed patterns. So a consumer never falls off the
normalized surface -- the untranslated case surfaces there in its original
form.

The inner emitter therefore has a real caller: someone holding string values
who is deliberately skipping the type layer, which is the same role `raw` plays
one level up. It is not an escape hatch for cases the surface cannot express.

Mechanism, if the two are exposed from one value: an attrset carrying
__functor is callable AND openable, so `emit xs` and `emit.<inner> ys` both
work with no module system and no override machinery. Measured.
<<<
RATIONALE: >>>
Recorded because the shape was argued to the wrong conclusion twice before
landing here -- first as two code paths that would drift, which was wrong since
it is one implementation composed, then as an escape hatch for the
inexpressible, which was wrong because the untranslated case never leaves the
normalized surface in the first place.
<<<
NOTES: >>>
OPEN, and deliberately not decided here: what the inner entry point is called
and whether it is exposed at all yet. It cannot be called faithful -- see
MECH-FAITHFUL-IS-NOT-A-CONSUMER-WORD. A leading underscore reads as private
across Nix, which is the wrong signal for something supported. Since __functor
makes adding it a one-line change later, waiting for a caller costs nothing and
removing a published attribute costs more than adding one.

IMPLEMENTED 2026-08-27. `lib/denormalize.nix` carries the encode halves and
`lib/sgra.nix` the file format; `lib/emit.nix` is the two composed, one entry
point per node type, derived from the renderer's own attribute names. The
renderer takes no `normalized` at all, which is what makes "no encoding on this
side" checkable rather than asserted. Both surfaces still render
docs/sdoc/grammar.sgra and fixtures/foreign.sgra byte for byte, and the
emitter-alone arm of the surface-live check still accepts every case it is meant
to, so the split moved no rejection across the type boundary.

Two boundary calls the sketch did not settle, both decided by what each half can
SEE. The `", "`-joined choice vocabulary is already a string by the time the
renderer runs, so "at least one option" is checked in denormalize -- the last
layer holding the list -- while "this kind needs a vocabulary at all" stays in
the renderer. And the file's spelling of each field kind and relation type
(`String`, `Parent`) stays in the renderer beside the other format constants: it
is not an encoded value, it is what the discriminator is called in the file.

__functor was not needed. The inner emitter is four renderers, not one function,
so the callable-and-openable trick has nothing to apply to unless a single entry
point is later published. The naming question above is still open, and nothing
outside `lib/emit.nix` reaches either half.
<<<

[MECHANISM]
UID: MECH-STRICTDOC-VERSION-SMOKE
TITLE: Nothing asserts the strictdoc binary's version any more
DEPTH: sketch
AUTHORED_BY: llm
STATEMENT: >>>
The retired first-party build asserted its own acceptance condition in an
installCheckPhase: `strictdoc version` had to print the version the sidecar
pinned, and that assertion was positive-controlled. Re-exporting upstream's
flake package took it away, because the package is extended by plain attrset
update -- `//`, not overrideAttrs -- precisely so its drvPath and outPath stay
identical to upstream's, and adding a phase would forfeit that.

So the whole class of "the seam evaluates fine and produces some other
version" is now unguarded. It was checked by hand at the switch (0.28.3, the
release main was sitting on) and by hand is where it stands.

Possible shapes, none costed: a separate flake check that runs
`${pkgs.ai.devTools.strictdoc}/bin/strictdoc version` and greps for the input's
locked rev-derived version; folding the same assertion into one of the two
existing strictdoc checks, which already have the binary on nativeBuildInputs;
or accepting that an upstream flake asserting its own version is upstream's job
and dropping the requirement.
<<<
RATIONALE: >>>
Worth recording because the loss is invisible: the package still builds, the
checks still pass, and the only signal that the assertion is gone is that the
file no longer contains it.
<<<

[MECHANISM]
UID: MECH-STRICTDOC-DEVENV-MODULE-NOT-PUBLISHED
TITLE: ai.strictdoc cannot be published as a devenv facet while options-doc demands exact HM parity
DEPTH: sketch
AUTHORED_BY: llm
STATEMENT: >>>
packages/strictdoc-grammar/modules/devenv/ is imported by PATH from devenv.nix
rather than exposed as modules.devenv on the package barrel, and that is a
constraint rather than a preference.

flake.nix builds devenvModules.nix-agentic-tools from collectFacet ["modules"
"devenv"], which walks every barrel. checks/options-doc.nix then diffs that
merged devenv option tree against homeManagerModules.default option name for
option name. Any ai.* option with a devenv facet and no home-manager facet
fails that check by construction, and ai.strictdoc has no home-manager half by
ruling (MECH-STRICTDOC-DEVENV-MODULE).

So there are three ways forward and none is free. Add a home-manager facet,
which the ruling declined. Teach options-doc an explicit devenv-only allowlist,
which weakens the parity gate for every future module. Or leave the module
unpublished, which is what happened, at the cost that a consumer of this
repository's flake cannot import ai.strictdoc at all -- only this repository's
own devenv.nix reaches it.

Nothing records the third cost anywhere a consumer would see it.
<<<
RATIONALE: >>>
Noticed while stripping the wrap out of the overlay: the module header asserted
this constraint and cited a node UID that did not exist, so the reasoning was
one edit away from being lost entirely.
<<<

[MECHANISM]
UID: MECH-SDOC-LOOP-SHELL-ENTRY-STAGES-FILES
TITLE: devenv shell -- strictdoc runs the enterTest DAG and stages the working tree
DEPTH: sketch
AUTHORED_BY: llm
STATEMENT: >>>
The sdoc skill's required loop is `strictdoc format .` then a clean export, and
strictdoc reaches a session only through `ai.strictdoc.enable`, so the obvious
way to run it from a worktree is `devenv shell -- strictdoc format .`. Measured
2026-08-27: that form runs devenv:enterTest first, which runs
devenv:git-hooks:run, which runs prek over the tree and lets treefmt-restage
`git add` whatever it touched. The hook run then reports FAILED (restage's own
signal that it modified files) while `strictdoc format` afterwards exits 0.

Two bad readings follow. The failure looks like the format loop failing, and a
working tree that was deliberately unstaged comes back fully staged -- neither
caused by anything the session was doing.

Fix shape: reach the binary rather than the environment. `nix build .#strictdoc
--print-out-paths` and prepend its bin, or give the module a task that runs the
loop, so the validation loop never depends on entering a shell.
<<<
RATIONALE: >>>
Hit while running the loop for the grammar-write wiring. Recorded because the
skill names the two commands and says nothing about how to reach them from a
worktree, which is the only place work happens here.
<<<

[MECHANISM]
UID: MECH-DEVENV-TASK-SCRIPTS-FIXED-AT-EVAL
TITLE: A devenv task cannot consume what another task in the same run regenerates
DEPTH: sketch
AUTHORED_BY: llm
STATEMENT: >>>
Repo-wide, not attached to any milestone. devenv renders every task's `exec`
into a script at EVALUATION and runs the graph afterwards, so anything a task
body interpolates out of Nix is fixed before the first task in the run starts. A
task that consumes what an earlier task in the same run regenerates therefore
sees the PRE-RUN value, and the failure is silent: the run reports success and
writes a stale artefact.

Measured 2026-08-27 while wiring generate:sgra.
`ai.strictdoc.grammars.<name>.rendered` is an evaluation-time string, so chaining
the write behind generate:sdoc-grammar:normalized would have emitted the grammar
rendered from the surface that existed when the run BEGAN -- in precisely the run
that regenerated it. The two are deliberately separate invocations and
generate:sdoc-grammar's log line names the follow-up rather than running it.

The generate:* graph is largely interpolation-free today and so does not hit
this, which is why it has never been noticed. Nothing detects the shape. The fix
in any given case is either a second invocation or a task body that READS the
file at run time instead of interpolating it, and the second only works where a
file is what is being passed.
<<<
RATIONALE: >>>
Recorded repo-wide rather than inside the grammar nodes because the reasoning has
nothing to do with strictdoc: it is a property of how devenv builds its task
graph. The next session to chain a generator behind a regeneration pays the same
cost, and pays it as a wrong output rather than as an error.
<<<

[MECHANISM]
UID: MECH-IDEMPOTENT-WRITER-UNCHANGED-IS-NOT-PROOF
TITLE: An idempotent writer reporting unchanged proves nothing about whether it can write
DEPTH: sketch
AUTHORED_BY: llm
STATEMENT: >>>
generate:sgra skips a file whose bytes already match and logs `unchanged`. So
does a run whose target path is wrong, whose cwd anchor is wrong, or whose
comparison is inverted. Every one of those logs `unchanged` and exits 0, against
a file it never touched, and the reassuring word is the same in all four cases.

The first run of the write task on 2026-08-27 reported exactly that against
docs/sdoc/grammar.sgra. It was believed only after DELETING the file and
re-running, which logged `wrote` and reproduced the committed bytes; that
sequence is what makes the write and the byte-identity claim one measurement
instead of two assertions sitting next to each other.

The shape is not local to this task: dev/tasks/generate.nix's `sync_file` has the
same blind spot, and so does any comparison-first writer. Fix shape, if one is
wanted, is to make the log carry the path that was compared, so a wrong anchor
prints a wrong path rather than a right-sounding word.
<<<
RATIONALE: >>>
Logged because the failure is silent and self-confirming in the direction a
session already wants to believe: a generator that appears to have nothing to do
is indistinguishable from a generator that is already correct.
<<<

[MECHANISM]
UID: MECH-SLICE-CANNOT-BE-SUPERSEDED
TITLE: A slice has no way to say it was replaced
DEPTH: sketch
AUTHORED_BY: llm
STATEMENT: >>>
`Superseded_By` is declared only on DECISION, so when a slice's subject is
replaced the only options are rewriting its statement in place or leaving it
describing something that no longer exists. Both lose the transition. Hit for
real on SLICE-STRICTDOC-OVERLAY, whose statement specified a first-party build
that the upstream flake switch retired. Decide whether the relation is extended
to the other node types, whether slices are collected differently, or whether
rewriting in place is the intended answer and the history belongs in the commit
rather than the graph.
<<<
RATIONALE: >>>
The graph records what is true now and, through fingerprints, when a contract
changed. It has no way to record that a unit of work was replaced wholesale,
which is a different event from either.
<<<

[MECHANISM]
UID: MECH-AI-STRICTDOC-HOME-PARITY
TITLE: Satisfy options parity with a home-level install, and defer the rest
DEPTH: sketch
AUTHORED_BY: llm
STATEMENT: >>>
checks/options-doc.nix demands exact home-manager parity for an `ai.*` facet, so
the devenv-only ai.strictdoc module fails by construction. Operator's ruling:
add a home-manager module carrying `enable` and `package` only -- a user-global
install, the same shape packages/semble/modules/homeManager already has -- which
satisfies parity as a bucket item.

`grammars` is deliberately NOT mirrored at the home level, and this is a
judgement rather than an omission: managing sdoc grammars for a user with no
defined project root does not fit. The operator maintains their own
configuration in a separate repository, as most home-manager users do, and
expects grammars to be maintained through devenv inside whichever repository
owns the documents.

That makes this a real exception to the repo's config-parity rule rather than a
gap to close later, so the parity language itself needs updating to say a
surface may be intentionally home-absent when it is inherently project-scoped.
<<<
RATIONALE: >>>
The parity rule exists so a feature is not quietly available in one place and
missing in another. A surface that is meaningless without a project root is not
that case, and forcing it into home-manager would produce an option nobody can
use correctly.
<<<
