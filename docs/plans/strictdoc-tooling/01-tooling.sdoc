[DOCUMENT]
TITLE: StrictDoc tooling for this repository

[GRAMMAR]
IMPORT_FROM_FILE: @repo

[DECISION]
UID: DEC-FINGERPRINT-IN-NODE
TITLE: Store the parent contract fingerprint in the node
AUTHORED_BY: llm
STATUS: accepted
RETIRES_ON: >>>
A second consumer needs per-edge state that a node field cannot carry, such as
a reviewer identity or a waiver with its own expiry.
<<<
STATEMENT: >>>
A node records the contract hash of each parent it depends on, in a PARENT_FP
field on the node itself, rather than in a sidecar file keyed by node identity.
Fingerprints point strictly downward: DECISION to MECHANISM to SLICE.
<<<
RATIONALE: >>>
Accepting a change becomes a reviewable git diff, attributable to a commit and
revertable. A sidecar makes sign-off invisible and needs a key-matching scheme.
The downward-only rule means a garbage-collectable node has no inbound
fingerprint, so deleting it can never strand one.
<<<

[DECISION]
UID: DEC-LOCAL-IMPLEMENTABILITY
TITLE: Implementability is a property of a closure, not of the project
AUTHORED_BY: llm
STATUS: accepted
RETIRES_ON: >>>
A release needs a single project-wide readiness answer, which no per-slice
query can supply.
<<<
STATEMENT: >>>
A slice is implementable when its own transitive contract-dependency closure is
settled and carries no suspect edges. There is no global readiness gate. The
count of open decisions in that closure is the slice's degrees of freedom, and
handoff is that count reaching zero.
<<<
RATIONALE: >>>
A global fail-closed gate is waterfall by construction: nothing is implementable
until everything is designed. A closure-local predicate lets a mature slice ship
while the rest of the graph stays deliberately fuzzy.
<<<

[DECISION]
UID: DEC-DEFER-LAYER
TITLE: Omit the LAYER node type until a corpus with layers arrives
AUTHORED_BY: llm
STATUS: open
RETIRES_ON: >>>
The first document whose mechanisms sit in distinct architectural layers, at
which point the cast tables' locus column becomes the LAYER assignment.
<<<
STATEMENT: >>>
The grammar ships without LAYER. Horizontal position is therefore unmodelled;
only the vertical axis, a SLICE and the mechanisms it Crosses, is expressible.
<<<
RATIONALE: >>>
No content in this document sits in a layer. Adding LAYER now would make every
MECHANISM carry a field with one possible value.
<<<
NOTES: >>>
This is a real gap, not a cost-free deferral: half the horizontal-and-vertical
tracking the operator asked for is absent until it is closed.
<<<

[MECHANISM]
UID: MECH-FP-CHECK
TITLE: Suspect-link detection over the JSON export
DEPTH: implemented
AUTHORED_BY: llm
STATEMENT: >>>
Hash each node's contract-bearing fields from the JSON export. A node is suspect
when a parent it records a fingerprint for no longer hashes to the recorded
value, or when that parent has been deleted. Excludes RATIONALE and NOTES.
<<<
RATIONALE: >>>
StrictDoc has no suspect-link feature. It is on the upstream backlog as
SDOC-SRS-117 and described unbuilt in their DO-178 notes.
<<<
PARENT_FP: DEC-FINGERPRINT-IN-NODE:0000000
RELATIONS:
- TYPE: Parent
  VALUE: DEC-FINGERPRINT-IN-NODE
  ROLE: Governed_By

[MECHANISM]
UID: MECH-CYCLE-CHECK
TITLE: Cycle detection over the JSON export
DEPTH: implemented
AUTHORED_BY: llm
STATEMENT: >>>
Detect relation cycles in the exported graph independently of StrictDoc.
<<<
RATIONALE: >>>
StrictDoc's own cycle detection queries the graph without specifying an edge
role, and the graph database returns only the bucket of role-less edges. Every
relation in this grammar carries a role, so no cycle in this corpus is detected;
the failure surfaces as a recursion-depth crash during render.
<<<
PARENT_FP: DEC-LOCAL-IMPLEMENTABILITY:0000000
NOTES: >>>
Implemented: dev/scripts/cycle-check.py, an iterative (non-recursive, so it
cannot hit the exact recursion-depth failure it replaces) DFS over every
Parent-type RELATIONS entry regardless of ROLE -- File relations excluded,
since their VALUE names a filesystem path, not a node. CI gate:
checks/strictdoc-cycle-check.nix, mirroring strictdoc-fp-check.nix's clean
$TMPDIR export harness (SLICE-FP-DETECTOR) rather than sharing its
derivation, so the two checks stay independently attributable on failure.

Verified past the happy path with two synthetic fixtures, not just the real
graph: a 3-node cycle where every edge carries a role (A --Assumes--> B
--Assumes--> C --Assumes--> A) is caught and reported with its role chain,
plus a disjoint acyclic pair in the same export to prove no cross-node false
positive; and an acyclic diamond (two paths converging on one node) plus a
File relation whose VALUE equals its own owning node's UID, to prove that
is not mistaken for a self-loop. Real graph: 61 nodes, 36 role-carrying
edges, 0 cycles found.

Positive control re-run independently at review, against the real graph rather than a fixture: a role-carrying two-cycle was injected by closing a loop back against an existing Governed_By edge. strictdoc export exited 0 and reported nothing; cycle-check exited 1 and named the path. The role-blind premise is therefore measured here, not inherited.
<<<
RELATIONS:
- TYPE: Parent
  VALUE: DEC-LOCAL-IMPLEMENTABILITY
  ROLE: Governed_By

[MECHANISM]
UID: MECH-READY-QUERY
TITLE: Ready-slice query over the contract closure
DEPTH: interface-settled
AUTHORED_BY: llm
STATEMENT: >>>
One function in dev/scripts/sdoc_fp.py walks a node's contract-dependency closure from the JSON export and returns a verdict record. dev/scripts/ready.py is its command line, beside cycle-check.py and fp-check.py. The closure follows every relation whose TYPE is Parent, regardless of role, and every PARENT_FP entry. The filter is on Parent rather than on not-File: a Child relation points downstream and is not a dependency, and a complement filter would walk one into the closure the day the grammar declares one.

The record carries, for one root: the root's own DEPTH or STATUS, held separate from its dependencies; whether every dependency is settled; the frontier, meaning the unsettled dependencies that have no unsettled dependency of their own, each with its hop distance from the root and the reason it blocks; how many unsettled nodes sit behind that frontier; the closure size; the open decisions in the closure, which are the degrees of freedom; and the suspect fingerprint entries whose node falls inside the closure, taken from fp-check's finding list rather than recomputed here.

Ready means every dependency is settled and the root itself is settled. What settled MEANS -- which DEPTH values qualify, and whether the cut differs by node type -- is not decided here: it is the single predicate MECH-READINESS-PREDICATE-RECONCILE owns, imported and never restated. A settled closure under an unsettled root is ready to design, which is a different action from ready to implement, and the record says which. The root never appears in its own blocker list.

ready.py prints the record as text, --json emits it verbatim, and --packet prints the closure through docs/sdoc/render.py in dependency-first order as the bounded brief handed to an implementing session. With no root it reports every SLICE. It exits 0 whenever the export parsed; --require-ready opts a caller into exit 1 on a blocked root.

Consumers: docs/sdoc/status.py drops its own closure_verdict and calls the shared function; fp-accept's readiness refusal calls the same predicate; the implementation-session prompt in docs/sdoc/README.md is replaced by --packet; and the milestone-four checkpoint wiring registers the record as gate evidence. The function is the interface and the script is one front end, so the tool from SLICE-SDOC-CLI imports it rather than reimplementing it.

Out of scope, deliberately. This node owns the traversal, the record and the report, not the rule: what settled means for a rejected, superseded or suspect parent is MECH-READINESS-PREDICATE-RECONCILE's single predicate, imported here and never restated. Nothing here writes, signs, or fails nix flake check.
<<<
RATIONALE: >>>
The query already exists informally and disagrees with itself. status.py's closure_verdict is one reading, sdoc_fp.is_ready another, and neither applies the no-suspect-edge clause the definition names. One function returning one record is what stops a fourth reading appearing when the milestone-two tool and the milestone-three behaviour model each need the same answer; a third standalone script would be the drift INV-GUARDS-MUST-EXECUTE names.

It reports and does not gate. DEC-LOCAL-IMPLEMENTABILITY refuses a global readiness gate, and the one time the graph said blocked the operator directed implementation anyway and it shipped clean, so a blocked verdict is information for whoever is deciding, not a refusal.

The record is specified as data with a text rendering rather than as printed output because a gate in milestone four has to consume the verdict, and parsing a report back out of a terminal is how the fifth definition of ready gets written.
<<<
PARENT_FP: DEC-LOCAL-IMPLEMENTABILITY:0000000
NOTES: >>>
Measured against the current export, 139 nodes, on 2026-08-27.

Closures are small enough to be a prompt. The deepest is SLICE-INSTANCE-SEMANTICS-MIGRATION at 34 nodes and 59,740 characters of field text, against 232,966 for the whole graph rendered by render.py --all. The packet is a quarter of the corpus, not a tenth, and that is the worst case in the graph today.

The frontier is a weaker filter than MECH-READINESS-REPORT-FRONTIER assumes. On that same slice, 21 unsettled dependencies excluding the root, of which 16 are in the frontier -- 10 of the 21 are sketch nodes with no dependencies at all, so they qualify by definition. The cut that actually shortens the report is hop distance: 5 of the 21 are direct dependencies and the closure is 4 hops deep. Hence both axes in the record. That node's "twenty-three blockers" measures 22 today including the root.

status.py does not apply the no-suspect-edge clause, measured rather than read. Replacing MECH-SEMBLE-EXTRA-GRAMMARS's PARENT_FP hash with a wrong non-placeholder value in a scratch copy of the export makes fp-check exit 1 reporting one suspect entry, while status.py's verdict for SLICE-SDOC-IN-SEMBLE, whose closure contains that node, is unchanged. Positive control on the same node and the same copy: setting its DEPTH to sketch does change the verdict, which prints the new blocker.

All 31 fingerprint entries currently have a matching relation, 0 unbacked, so the relation set and the PARENT_FP set coincide. MECH-FP-RELATION-LINT is a check and not a write-time invariant, so the walk still unions them; ignoring the fingerprint half is how an earlier status.py reported a blocked slice as ready.

Degrees of freedom is not a headline on its own. Seven of the twelve slices are blocked with zero open decisions in their closure, because unsettled mechanisms do not move the count; only SLICE-CHECKPOINT-WIRING at 1 and SLICE-INSTANCE-SEMANTICS-MIGRATION at 2 have any.

MECH-READY-QUERY-GRAPH-REUSE is answered: cycle-check.py's build_graph is this walk minus PARENT_FP, so it moves into sdoc_fp.py with a flag for whether fingerprint parents count as edges.

MECH-READINESS-REPORT-FRONTIER is subsumed. Both of its complaints -- the root reporting itself as its own blocker, and an undifferentiated blocker list -- are answered by this record, so it closes when this lands rather than being groomed separately.

LEFT TO THE OPERATOR, deliberately. This milestone settles the plumbing;
each of these is a rule about how this instance works and milestone five is
where they get written.

- What settled means for a rejected, superseded or suspect parent. Deliberately not decided here; it is MECH-READINESS-PREDICATE-RECONCILE's single predicate, and this node consumes it as a parameter.

- Whether the closure stops at a settled node or walks through it into that node's own unsettled dependencies. Live instance: SLICE-SDOC-IN-SEMBLE is verified yet reports blocked, because it crosses MECH-SEMBLE-EXTRA-GRAMMARS (implemented) whose Governed_By parent DEC-ARCH-COLOCATION is open. Filed as a backlog DECISION.

- Whether relation roles weigh differently in the closure. The walk treats Governed_By, Crosses, Assumes, Proven_By and Guarantees identically; whether an Assumes edge should block as hard as a Crosses edge is a semantic call, filed as a backlog DECISION.

- Whether readiness ever becomes a merge or commit gate. Specified here as advisory with an opt-in --require-ready flag, so milestone four can arm it without this node choosing the policy.

- Which DEPTH values count as settled, and whether the cut differs per node type. DEPTH is instance-layer by MECH-SEMANTICS-DEFINITION-BOUNDARY's own wording, so this node declares the traversal and imports the cut rather than fixing it.
<<<
RELATIONS:
- TYPE: Parent
  VALUE: DEC-LOCAL-IMPLEMENTABILITY
  ROLE: Governed_By

[SPIKE]
UID: SPIKE-SGRA-PARSE
TITLE: Make the tree-sitter grammar parse standalone .sgra files
DEPTH: implemented
AUTHORED_BY: llm
STATUS: run
RETIRES_ON: >>>
A three-rule patch is applied and the two .sgra files parse with no regression
across the sdoc corpus.
<<<
STATEMENT: >>>
The upstream tree-sitter grammar parses all sdoc documents but fails every
standalone .sgra grammar file, because its root rule requires a DOCUMENT header.
<<<
NOTES: >>>
Run. The DOCUMENT-header fix alone was not sufficient: our own grammar.sgra
also uses REVERSE_ROLE on every non-File Parent relation, and upstream's
grammar_relation_parent/child rules had no field for it at all, so it still
errored after the root-rule fix. The applied patch is therefore three rule
changes across two files (source_file's root choice, a new standalone_grammar
rule, and REVERSE_ROLE added to both relation rules) rather than one.

Measured against this repo's own corpus (6 .sdoc + grammar.sgra): 6/7 clean
before the patch, 7/7 after. Measured against strictdoc-project/strictdoc's
own docs/ (15 files, pinned rev 215cda2e): 5/15 clean both before and after —
the other 10 fail on pre-existing document-body/FREETEXT coverage gaps this
patch never targeted (out of DEC-GRAMMAR-PATCH-NOT-FORK's scope; logged as
MECH-SGRA-BODY-COVERAGE in the plan backlog). checks/strictdoc-grammar-corpus.nix
is the standing regression gate against both corpora.
<<<

[SLICE]
UID: SLICE-SDOC-IN-SEMBLE
TITLE: Index sdoc documents in semble
DEPTH: verified
AUTHORED_BY: llm
STATEMENT: >>>
Package a tree-sitter grammar for the sdoc format as a flake output, add it to
ai.programs.semble.grammars, and register a path mapping assigning *.sdoc to
that language in the docs index. Add a load check modelled on the existing
extra-grammars check, parsing a real sdoc sample.
<<<
RATIONALE: >>>
The repository's flake instructions already require that a custom grammar absent
from nixpkgs be exposed as a flake package so the authenticated matrix publishes
it. Every mechanism this slice crosses is already implemented.
<<<
NOTES: >>>
Implemented: overlays/generic/tree-sitter-strictdoc.nix (flake package
tree-sitter-strictdoc, flattened via pkgs.ai.generic), wired into
ai.codex.programs.semble.grammars and mcp.pathMappings in devenv.nix (patterns
*.sdoc and *.sgra, content docs). Load check:
checks/module-eval.nix:module-semble-strictdoc-grammar-load. Regression/corpus
suite: checks/strictdoc-grammar-corpus.nix (see SPIKE-SGRA-PARSE for measured
counts). update-targets and cache-hit-parity rows added; both checks pass.

Chunking verified independently, not assumed: on a 8762-byte document the AST
chunker returns 17 chunks against line chunking's 12, and the boundaries land
on node headers and on field starts, so a node larger than the 750-character
target splits into its own fields. chunk() returning a list rather than None is
the proof the parser loaded; a fallback would have been a log warning only.
<<<
RELATIONS:
- TYPE: Parent
  VALUE: MECH-SEMBLE-EXTRA-GRAMMARS
  ROLE: Crosses
- TYPE: Parent
  VALUE: MECH-SEMBLE-PATH-MAPPINGS
  ROLE: Crosses
- TYPE: Parent
  VALUE: SPIKE-SGRA-PARSE
  ROLE: Proven_By

[SLICE]
UID: SLICE-FP-DETECTOR
TITLE: Suspect-link detection and acceptance over the design graph
DEPTH: implemented
AUTHORED_BY: human
STATEMENT: >>>
Ship fp-check and fp-accept over the JSON export, plus a flake check that gates
on fp-check with a clean output directory.

fp-check hashes each node's contract-bearing fields and compares every
PARENT_FP entry against the current hash of the parent it names. It reports
three cases distinctly: never signed, where the recorded hash is the
placeholder; drifted, where a real recorded hash no longer matches; and
unbacked, where a fingerprint names a parent the node has no relation to.

fp-accept rewrites the named nodes' entries to current hashes and is the only
thing that writes them. It refuses a parent that is still moving.
<<<
RATIONALE: >>>
The contract field selection is a prototype choice, deliberately not settled --
see MECH-FP-FIELD-TUNING. Git-flow handling is deliberately absent: nothing
bites before a branch reaches main, and that merge is the forcing function.
<<<
PARENT_FP: >>>
MECH-FP-ACCEPT-READINESS:0000000
MECH-FP-CHECK:0000000
MECH-FP-RELATION-LINT:0000000
<<<
NOTES: >>>
Implemented: dev/scripts/fp-check.py and fp-accept.py, sharing dev/scripts/
sdoc_fp.py (contract-field hashing, PARENT_FP parsing, the readiness
predicate) and sdoc_edit.py (structural PARENT_FP field editor -- finds a
node's line-range by UID and field-range by name rather than splitting on
blank lines, because a multiline field's own prose can contain blank
paragraph breaks). CI gate: checks/strictdoc-fp-check.nix, exporting the
whole graph into a fresh runCommand $TMPDIR on every build. strictdoc added
to the interactive devShell (devenv.nix) for the skill's format/export loop
and for running these scripts by hand.

fp-check's first real run over this repo's existing graph found 5 nodes
across docs/plans/beads-migration and packages/semble/.sdoc with a PARENT_FP
entry and no matching relation -- exactly MECH-FP-RELATION-LINT's predicted
defect class, not a tooling bug. Fixed as their own commit (the missing
Governed_By edge each PARENT_FP already implied; nothing else about those
nodes changed) before wiring the check into flake.nix, so the gate starts
green rather than red on day one.

Verified past the happy path: a synthetic export exercises all four
fp-check cases (signed-and-current, never-signed, drifted, unbacked) plus a
deleted-parent case in one run, and a synthetic readiness fixture confirms
fp-accept actually refuses a DECISION parent with STATUS open and a
MECHANISM parent below interface-settled rather than silently skipping the
check. fp-accept was then run for real on SLICE-FP-DETECTOR itself (this
node) and on MECH-FP-CHECK and MECH-FP-ACCEPT-READINESS, producing the
PARENT_FP entries above and below -- the multi-entry block form is this
node's own three-parent write, exercised for real rather than only in the
synthetic fixture.
<<<
RELATIONS:
- TYPE: Parent
  VALUE: MECH-FP-CHECK
  ROLE: Crosses
- TYPE: Parent
  VALUE: MECH-FP-ACCEPT-READINESS
  ROLE: Crosses
- TYPE: Parent
  VALUE: MECH-FP-RELATION-LINT
  ROLE: Crosses

[MECHANISM]
UID: MECH-FP-RELATION-LINT
TITLE: Every PARENT_FP entry should have a matching relation
DEPTH: implemented
AUTHORED_BY: llm
STATEMENT: >>>
A node recording a fingerprint for a parent asserts a dependency on that
parent's contract, so it should also carry an edge to it. Nothing enforces
that today, and several nodes in this graph already have a fingerprint with no
corresponding relation.
<<<
RATIONALE: >>>
Without the lint the two can disagree silently, and the edge is what the
traversal follows. A fingerprint the traversal cannot reach is invisible to both
the drift check and the render cache.
<<<
NOTES: >>>
Realized as fp-check's "unbacked" case (dev/scripts/fp-check.py) rather than
a separate binary -- the check already walks every PARENT_FP entry against
the node's RELATIONS, so a second pass over the same data would just be the
first one run twice. Its first real run over this repo's own graph found 5
pre-existing violations; see SLICE-FP-DETECTOR's NOTES.
<<<

[MECHANISM]
UID: MECH-SDOC-CI-CHECK
TITLE: Gate the design graph in nix flake check
DEPTH: implemented
AUTHORED_BY: llm
STATEMENT: >>>
Add a flake check that exports the graph to JSON and fails on non-zero exit, so
a broken relation or an invalid enum value cannot merge.
<<<
RATIONALE: >>>
Validation currently runs only when someone remembers to run it. The export is
a few seconds on a corpus this size.
<<<
NOTES: >>>
The check must use a clean output directory. Incremental generation produces a
false green: the same broken input exits 1, then 0 on re-run against a warm
output directory.

Determined by SLICE-GRAPH-CHECKS: satisfied as a byproduct, no separate check
added. checks/strictdoc-fp-check.nix (SLICE-FP-DETECTOR) runs `strictdoc
export` under `set -euETo pipefail` inside a clean runCommand $TMPDIR --
validation runs at parse time, so a non-zero export exit already fails that
build. checks/strictdoc-cycle-check.nix (MECH-CYCLE-CHECK) does the same
independently. Two checks now provide this gate; adding a third binary whose
only job was the export step itself would just be the same export run a
third time.
<<<

[SLICE]
UID: SLICE-GRAPH-CHECKS
TITLE: Make the graph fail loud on cycles and on an unvalidated export
DEPTH: verified
AUTHORED_BY: human
STATEMENT: >>>
Two checks over the JSON export, in the harness fp-check already established.

Cycle detection, because StrictDoc's own is blind to relations that carry a
role and every relation here carries one -- a cycle currently surfaces as a
recursion crash during render rather than an error.

An export gate, so a malformed document cannot reach the branch. Determine
first whether checks/strictdoc-fp-check.nix already provides this as a
byproduct of its clean-directory export; if it does, say so and close
MECH-SDOC-CI-CHECK rather than adding a second binary.
<<<
RATIONALE: >>>
Both are small and both close holes that have already been hit. A broken graph
was committed to this branch and the hooks passed it. Cycles have never been
tested because nothing detects them.
<<<
NOTES: >>>
Cycle detection: MECH-CYCLE-CHECK. Export gate: determined already satisfied
as a byproduct of checks/strictdoc-fp-check.nix and, now, also of
checks/strictdoc-cycle-check.nix -- see MECH-SDOC-CI-CHECK's NOTES for the
determination. No second export-only binary added.
<<<
RELATIONS:
- TYPE: Parent
  VALUE: MECH-CYCLE-CHECK
  ROLE: Crosses
- TYPE: Parent
  VALUE: MECH-SDOC-CI-CHECK
  ROLE: Crosses

[SPIKE]
UID: SPIKE-EXECUTABLE-RULES
TITLE: How much of the design system's rules can run rather than be read
DEPTH: interface-settled
AUTHORED_BY: llm
STATUS: run
RETIRES_ON: >>>
An assessment the operator has reviewed answers all four questions -- a grammar
generated from a typed Nix option surface, the state machine and flows that
gate an sdoc's creation and change, validation tiers with measured costs, and
whether the strictdoc package needs a first-party overlay -- and each finding
is either carved into a slice or explicitly declined. A question the assessment
cannot answer is recorded as a node rather than left implicit.
<<<
STATEMENT: >>>
INV-GUARDS-MUST-EXECUTE records a measured split: every constraint that lived
in a document failed and every executable one held. This spike assesses how
much of the design system's rules can be made to run rather than be read, in
four parts: generating docs/sdoc/grammar.sgra from a typed Nix module with no
untyped escape hatches; modelling the flows that create and change an sdoc as a
state machine, and capturing as nodes whatever resists modelling; tiering
validation by trigger and cost, from the native
traceability_index_build_finished hook to a CLI wrapper built on strictdoc
manage new; and whether any of that needs a first-party strictdoc overlay
rather than the nixpkgs package.

Assessment only. It creates no tasks, does not settle the contract field
selection (MECH-FP-FIELD-TUNING owns that), and does not touch git-flow
handling (MECH-FP-GIT-FLOW-HAZARDS).
<<<
RATIONALE: >>>
The operator has no picture of the state machine and is guessing when asked to
weigh in on it, and the field selection cannot be reviewed as prose either
(DEC-FP-FIELDS-CONFIGURABLE). A measured assessment with a rendered state
machine and a sketched option surface is what turns those guesses into
reviewable decisions.
<<<
PARENT_FP: >>>
DEC-FP-FIELDS-CONFIGURABLE:0000000
DEC-SYSTEM-PURPOSE:0000000
<<<
NOTES: >>>
Run 2026-08-25. The assessment is held in the operator's working area outside
the repository, with the four finder reports, eight contest files, critic pass,
logs and the Q1 prototype beside it; a fold-in review against two outside
research documents followed the same day. Thirteen agents: one finder per question, a refuter and a defender per report,
one cross-question critic; nine refuter-defender splits are surfaced for the
operator, none adjudicated. RETIRES_ON is not yet met: the operator has not
reviewed it.

Measured, on this corpus with nixpkgs strictdoc 0.27.1. The traceability
index build is 3 ms and the plugin hook body is under 1 ms; the cost of every
command is interpreter and imports 0.4 s, ProjectConfig.default_formats() 0.7
to 1.0 s, and the forkserver parallelizer 1.4 s. Pinning
formats=[SDocFormat(), JSONFormat()] takes export from 3.2 to 1.24 s, manage
new from 3.2 to 1.15 s and format from 3.3 to 1.15 s with a byte-identical
JSON export. The user_plugin hook fires on export, format, manage auto-uid and
server, never on manage new; a Format subclass in formats intercepts every
document read on every command, including manage new, inside the workers. A
hook class defined in strictdoc_config.py crashes every parallelised command
on 0.27.1 until the config inserts its own directory on sys.path.

A typed evalModules surface with no untyped option regenerates grammar.sgra
byte for byte (4085 bytes, 0.03 s): an ordered field catalogue plus per-element
typed subset selection, STATUS the one polymorphic slot. Thirteen of thirteen
bad declarations are rejected only once apply forces the merged value with
deepSeq -- two passed lazily and emitted a plausible grammar before that --
and addCheck's predicate is never called for a submodule in the pinned lib.
strictdoc rejects six of six injected grammar defects, two of them only
through the documents, so the gate exports the corpus and needs no first-party
package.

Of four levels -- node, edge, document, branch -- only the parser and the fp
and cycle checks execute, and only in CI. The parser accepts DEPTH TBD, a
Governed_By pointing at a MECHANISM, and an edit to an accepted decision's
statement. All four hashes reverted in 387cdaec equal today's, so a restored
signature reads as signed and current. Two live violations each of
INV-NO-EXTERNAL-PLAN-REFS and of the role-target table; five definitions of
ready that no two agree on. Ten incidentals logged to 99-backlog.

The package does not need owning for anything questions one or three need.
Seed facts held except: the version delta needs a reqif override plus a
pygments relax; of the six unused nixpkgs-only dependencies only graphviz,
pybtex and setuptools cost closure, the other three return through
html2pdf4doc; the three-derivation claim was found nowhere.
<<<
RELATIONS:
- TYPE: Parent
  VALUE: DEC-FP-FIELDS-CONFIGURABLE
  ROLE: Governed_By
- TYPE: Parent
  VALUE: DEC-SYSTEM-PURPOSE
  ROLE: Governed_By
