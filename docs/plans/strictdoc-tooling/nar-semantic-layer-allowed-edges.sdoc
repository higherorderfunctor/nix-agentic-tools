[DOCUMENT]
TITLE: Which relations are allowed

[GRAMMAR]
IMPORT_FROM_FILE: @repo

[NARRATIVE]
UID: NAR-SEMANTIC-LAYER-ALLOWED-EDGES
TITLE: Which relations are allowed
AUTHORED_BY: llm
WIDGET: rows
PLACE: screen
STATEMENT: >>>
Each role, what it may point at, how many are live, and what nothing checks.

- strictdoc checks only that a relation's role is registered on the source type and that its target exists. It never checks the target's type, the direction, or cycles. Eighteen (source type, role) pairs are live, plus File links on three types.
> strictdoc checks: ROLE registered on SOURCE type (fatal), Parent VALUE resolves (fatal); never target type, direction, cycles. Live: 18 (type, role) pairs + File on MECHANISM|SLICE|SPIKE [WORKS]
- A check that each role points at a legal target type was designed with 13 rows, is unbuilt, and is five rows short of the 18 pairs actually in use. Two settled nodes give different tables, and neither covers the ruled types.
[LINK: NAR-SEMANTIC-LAYER-GAP-GRAMMAR-CANNOT-SPELL-THE-VOCABULARY]
> target-type lint (source type, role) -> legal targets: 13 rows, unbuilt, 5 short of the 18 pairs; two settled tables disagree; no table for grid types exists [GAP]
- Governed_By points at a decision (65 live edges from mechanisms, work, requirements and probes). The grid adds a requirement as a legal target, and two edges still point at the wrong kind of node.
[LINK: NAR-SEMANTIC-LAYER-TYPE-DECISION] [LINK: NAR-SEMANTIC-LAYER-TYPE-REQUIREMENT]
> Governed_By: MECHANISM|SLICE|INVARIANT|SPIKE -> DECISION (65); grid adds a REQUIREMENT target; 2 miscast edges still live [GAP]
- Crosses (35 live edges, work to mechanism) is the lane a piece of work declares. But no node records which layer it belongs to, so 'crosses more than one layer' — what used to make a piece of work a 'slice' — has nothing to read.
[LINK: DEC-DEFER-LAYER] [LINK: NAR-SEMANTIC-LAYER-TYPE-WORK] [LINK: NAR-SEMANTIC-LAYER-TYPE-MECHANISM] [LINK: NAR-SEMANTIC-LAYER-GAP-SEMANTICS-LIVE-IN-TOOLS-WITH-NO-OWNER]
> Crosses: SLICE -> MECHANISM (35) = the lane; no node carries LAYER, so "crosses more than one layer" has no input [OPEN: DEC-DEFER-LAYER]
- Assumes (17 live edges, none fingerprinted) is undecided: does it carry a contract like the other roles?
[LINK: DEC-ASSUMES-CONTRACT-BEARING] [LINK: NAR-SEMANTIC-LAYER-TYPE-MECHANISM] [LINK: NAR-SEMANTIC-LAYER-TYPE-WORK] [LINK: NAR-SEMANTIC-LAYER-TYPE-DECISION]
> Assumes: MECHANISM -> DECISION|MECHANISM, SLICE -> DECISION|SLICE (17 live, 0 fingerprinted); contract-bearing? [OPEN: DEC-ASSUMES-CONTRACT-BEARING]
- Guarantees (2 live edges) points from a mechanism at the rule it upholds — read as a requirement.
[LINK: NAR-SEMANTIC-LAYER-TYPE-MECHANISM] [LINK: NAR-SEMANTIC-LAYER-TYPE-REQUIREMENT]
> Guarantees: MECHANISM -> INVARIANT (2), read as -> REQUIREMENT [WORKS]
- Superseded_By (2 live) is written on the retired decision, pointing at its successor. The plan is to extend it to other types once a second case appears in prose. Who may supersede is unstated.
[LINK: DEC-SUPERSESSION-RULE] [LINK: NAR-SEMANTIC-LAYER-TYPE-DECISION]
> Superseded_By: DECISION -> DECISION (2), written on the retired node; extend at the second prose instance; who may supersede: unstated [OPEN: DEC-SUPERSESSION-RULE]
- That extension list still names two of the dissolved types (what the grammar spells SLICE and INVARIANT) and omits requirement, use case and evidence.
[LINK: DEC-NODE-TYPE-GRID] [LINK: NAR-SEMANTIC-LAYER-TYPE-DECISION] [LINK: NAR-SEMANTIC-LAYER-TYPE-REQUIREMENT] [LINK: NAR-SEMANTIC-LAYER-TYPE-USE-CASE] [LINK: NAR-SEMANTIC-LAYER-TYPE-EVIDENCE] [LINK: NAR-SEMANTIC-LAYER-GAP-GRAMMAR-CANNOT-SPELL-THE-VOCABULARY]
> that extension list names SLICE, INVARIANT and omits REQUIREMENT|USE CASE|EVIDENCE [FALLS OUT: DEC-NODE-TYPE-GRID]
- Two mechanisms have been superseded in prose only, so the count that is supposed to trigger the extension reads zero.
[LINK: MECH-GROOMED-NODES-STAY-IN-THE-BACKLOG-FILE] [LINK: MECH-PLAN-BEADS-SNAPSHOT] [LINK: NAR-SEMANTIC-LAYER-TYPE-MECHANISM]
> prose-supersession ledger reads 0; MECH-GROOMED-NODES-STAY-IN-THE-BACKLOG-FILE and MECH-PLAN-BEADS-SNAPSHOT are prose-superseded [GAP]
- Backlogged_In links an ungroomed item to its plan's register. Grooming drops the edge.
[LINK: NAR-SEMANTIC-LAYER-TYPE-DECISION] [LINK: NAR-SEMANTIC-LAYER-TYPE-MECHANISM]
> Backlogged_In: any -> register; grooming drops the edge [WORKS]
- Nothing outside a plan may depend on a node inside it, and another plan counts as outside. The rule is keyed on file location. Two live edges violate it, and the check is unbuilt.
[LINK: NAR-SEMANTIC-LAYER-TYPE-REQUIREMENT] [LINK: NAR-SEMANTIC-LAYER-GAP-MERGE-BOUNDARY-IS-NOT-A-JOINT]
> direction: no Parent or PARENT_FP into docs/plans/<P>/ from outside (plan-to-plan counts); keyed on file; 2 live violations; check unbuilt [WORKS]
- Fingerprints are supposed to point strictly downward — decision to mechanism to work. Live entries from requirements to decisions, probes to decisions, and mechanism to mechanism sit off that ladder, and the direction has not said what to do with them.
[LINK: NAR-SEMANTIC-LAYER-TYPE-DECISION] [LINK: NAR-SEMANTIC-LAYER-TYPE-MECHANISM] [LINK: NAR-SEMANTIC-LAYER-TYPE-WORK] [LINK: NAR-SEMANTIC-LAYER-TYPE-REQUIREMENT] [LINK: NAR-SEMANTIC-LAYER-TYPE-EVIDENCE]
> fingerprint ladder DECISION -> MECHANISM -> SLICE strictly down; live INV->D, SPIKE->D, M->M sit off it [UNADDRESSED]
- Cycles among relations are caught by the repo's own check, run in nix flake check; strictdoc has no cycle check of its own.
[LINK: MECH-CYCLE-CHECK]
> cycles over roled Parent edges: MECH-CYCLE-CHECK in nix flake check [WORKS]
<<<
PARENT_FP: >>>
DEC-ASSUMES-CONTRACT-BEARING:0000000
DEC-DEFER-LAYER:0000000
DEC-NODE-TYPE-GRID:0000000
DEC-SUPERSESSION-RULE:0000000
MECH-CYCLE-CHECK:0000000
MECH-GROOMED-NODES-STAY-IN-THE-BACKLOG-FILE:0000000
MECH-PLAN-BEADS-SNAPSHOT:0000000
NAR-SEMANTIC-LAYER-GAP-GRAMMAR-CANNOT-SPELL-THE-VOCABULARY:0000000
NAR-SEMANTIC-LAYER-GAP-MERGE-BOUNDARY-IS-NOT-A-JOINT:0000000
NAR-SEMANTIC-LAYER-GAP-SEMANTICS-LIVE-IN-TOOLS-WITH-NO-OWNER:0000000
NAR-SEMANTIC-LAYER-TYPE-DECISION:0000000
NAR-SEMANTIC-LAYER-TYPE-EVIDENCE:0000000
NAR-SEMANTIC-LAYER-TYPE-MECHANISM:0000000
NAR-SEMANTIC-LAYER-TYPE-REQUIREMENT:0000000
NAR-SEMANTIC-LAYER-TYPE-USE-CASE:0000000
NAR-SEMANTIC-LAYER-TYPE-WORK:0000000
NAR-TERM-STRICTDOC:0000000
<<<
RELATIONS:
- TYPE: Parent
  VALUE: NAR-SEMANTIC-LAYER-GAP-GRAMMAR-CANNOT-SPELL-THE-VOCABULARY
  ROLE: Cites
- TYPE: Parent
  VALUE: NAR-SEMANTIC-LAYER-TYPE-DECISION
  ROLE: Cites
- TYPE: Parent
  VALUE: NAR-SEMANTIC-LAYER-TYPE-REQUIREMENT
  ROLE: Cites
- TYPE: Parent
  VALUE: DEC-DEFER-LAYER
  ROLE: Cites
- TYPE: Parent
  VALUE: NAR-SEMANTIC-LAYER-TYPE-WORK
  ROLE: Cites
- TYPE: Parent
  VALUE: NAR-SEMANTIC-LAYER-TYPE-MECHANISM
  ROLE: Cites
- TYPE: Parent
  VALUE: NAR-SEMANTIC-LAYER-GAP-SEMANTICS-LIVE-IN-TOOLS-WITH-NO-OWNER
  ROLE: Cites
- TYPE: Parent
  VALUE: DEC-ASSUMES-CONTRACT-BEARING
  ROLE: Cites
- TYPE: Parent
  VALUE: DEC-SUPERSESSION-RULE
  ROLE: Cites
- TYPE: Parent
  VALUE: DEC-NODE-TYPE-GRID
  ROLE: Cites
- TYPE: Parent
  VALUE: NAR-SEMANTIC-LAYER-TYPE-USE-CASE
  ROLE: Cites
- TYPE: Parent
  VALUE: NAR-SEMANTIC-LAYER-TYPE-EVIDENCE
  ROLE: Cites
- TYPE: Parent
  VALUE: MECH-GROOMED-NODES-STAY-IN-THE-BACKLOG-FILE
  ROLE: Cites
- TYPE: Parent
  VALUE: MECH-PLAN-BEADS-SNAPSHOT
  ROLE: Cites
- TYPE: Parent
  VALUE: NAR-SEMANTIC-LAYER-GAP-MERGE-BOUNDARY-IS-NOT-A-JOINT
  ROLE: Cites
- TYPE: Parent
  VALUE: MECH-CYCLE-CHECK
  ROLE: Cites
- TYPE: Parent
  VALUE: NAR-TERM-STRICTDOC
  ROLE: Cites
