[DOCUMENT]
TITLE: strictdoc_config.py must put itself on sys.path before defining a hook class

[GRAMMAR]
IMPORT_FROM_FILE: @repo

[EVIDENCE]
UID: MECH-SDOC-CONFIG-HOOK-IMPORTABILITY
TITLE: strictdoc_config.py must put itself on sys.path before defining a hook class
AUTHORED_BY: llm
STATEMENT: >>>
On nixpkgs strictdoc 0.27.1, any Format or StrictDocPlugin subclass defined in
strictdoc_config.py crashes every parallelised command -- export with the
default parallelizer, format, manage new, manage auto-uid -- with
ModuleNotFoundError: strictdoc_config in the forkserver workers.
helpers/module.py loads the config by file path without touching sys.path, and
the workers unpickle a ProjectConfig that carries the hook instance. Only
export --no-parallelization survives.

Measured fix: sys.path.insert(0, dirname(abspath(__file__))) as the config's
first statement. All four commands then work, for inline hook classes and for
sibling modules alike. Put the line in the config and in the skill's gotcha
list; drop it once nixpkgs lands >= 0.28.1, whose helpers/module.py does it.
<<<
RATIONALE: >>>
Measured by SPIKE-EXECUTABLE-RULES. Any plugin or Format-seam guard is dead on
arrival without it, and the failure presents as a crash in a worker rather than
as a config error. The upstream fix is the same line moved into the tool, so a
version bump is a convenience here, not a capability.
<<<
COMMENT: >>>
Retyped from MECHANISM to EVIDENCE on 2026-08-30 by the mechanism mood test under DEC-NODE-FAMILIES, with medium confidence after a second opinion: it records what was observed once, not how something always behaves. Noted for a later split: Title "must put itself on sys.path before defining a hook class" and "Put the line in the config and in the skill's gotcha list" read as a rule / work instruction but are a version-bound workaround. A reader could sort the crash description (helpers/module.py loads by path without touching sys.path; forkserver workers unpickle the hook) as a mechanism of 0.27.1. The UID keeps its prefix: DEC-UID-OUTLIVES-TYPE.
<<<
RELATIONS:
- TYPE: Parent
  VALUE: MECH-BACKLOG-STRICTDOC-TOOLING
  ROLE: Backlogged_In
