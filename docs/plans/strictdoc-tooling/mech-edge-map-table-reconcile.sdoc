[DOCUMENT]
TITLE: Two settled role tables disagree on three rows

[GRAMMAR]
IMPORT_FROM_FILE: @repo

[EVIDENCE]
UID: MECH-EDGE-MAP-TABLE-RECONCILE
TITLE: Two settled role tables disagree on three rows
AUTHORED_BY: llm
STATEMENT: >>>
`MECH-CORPUS-EDGE-MAP` states Assumes = MECHANISM to DECISION, Proven_By = MECHANISM or INVARIANT to SPIKE, and Governed_By = MECHANISM to DECISION. Measured over the live graph, none of the three holds: zero MECHANISM Assumes DECISION edges against 7 MECHANISM-to-MECHANISM, 6 SLICE-to-SLICE and 1 SLICE-to-DECISION; zero MECHANISM or INVARIANT Proven_By against 7 SLICE-to-SPIKE; and Governed_By sourced from SLICE (12), INVARIANT (3) and SPIKE (6) as well as MECHANISM (18). `MECH-RELATION-TARGET-TYPE-LINT` takes the union, reading `MECH-CORPUS-EDGE-MAP` as a forecast of how one unconverted corpus will be converted rather than as a graph-wide contract. Decide whether that reading stands, and if it does, whether per-plan profiles are a thing the lint supports at all.
<<<
RATIONALE: >>>
The reading is not free. The narrow Assumes rule was justified as cycle avoidance, and taking the union drops that constraint — safe only because `MECH-CYCLE-CHECK` now detects cycles in CI, which it did not when the narrow rule was written. `MECH-CORPUS-EDGE-MAP`'s STATEMENT is a contract field on a fingerprinted node, so the edit is the operator's and cannot be made here.
<<<
COMMENT: >>>
Cited by UID in `MECH-RELATION-TARGET-TYPE-LINT`'s COMMENT and again in its LEFT TO THE OPERATOR list. Counts measured 2026-08-27 against a clean export of 144 nodes, 92 Parent relations.

Retyped from MECHANISM to EVIDENCE on 2026-08-30 by the mechanism mood test under DEC-NODE-FAMILIES, with high confidence after a second opinion: it records what was observed once, not how something always behaves. Noted for a later split: 'Decide whether that reading stands, and if it does, whether per-plan profiles are a thing the lint supports at all' is an open question for the operator (work/register), and 'MECH-RELATION-TARGET-TYPE-LINT takes the union, reading MECH-CORPUS-EDGE-MAP as a forecast' describes the lint's reading (mechanism); neither is a rule. The UID keeps its prefix: DEC-UID-OUTLIVES-TYPE.
<<<
RELATIONS:
- TYPE: Parent
  VALUE: MECH-BACKLOG-STRICTDOC-TOOLING
  ROLE: Backlogged_In
