[DOCUMENT]
TITLE: Grooming must surface contradictions, not just missing edges

[GRAMMAR]
IMPORT_FROM_FILE: @repo

[REQUIREMENT]
UID: MECH-GROOM-CONTRADICTION-CHECK
TITLE: Grooming must surface contradictions, not just missing edges
AUTHORED_BY: human
STATEMENT: >>>
When a node is groomed, check whether an edge is missing that should exist, and
whether an existing edge now contradicts what the node says. Surface the
collision rather than silently resolving it.

A live example to test against: DEC-FP-ACCEPT-AUTHORITY holds that human-only
signing is too blunt and should key on grade. At least three places currently
assert human-only outright -- the authoring skill's hard rule, the acceptance
language in DEC-LONG-LIVED-BRANCH, and the two-keys split recorded in lifecycle
notes. None of them cite DEC-FP-ACCEPT-AUTHORITY and none is edged to
it, so nothing connects the open question to the assertions it contradicts.
<<<
RATIONALE: >>>
This is the failure the whole system exists to catch, and it is currently
uncaught in its own graph. The author's stated reason for building this is
returning to a conclusion having forgotten the reasoning; a contradiction with
no edge between its two halves is exactly that, made durable.
<<<
COMMENT: >>>
Retyped from MECHANISM to REQUIREMENT on 2026-08-30 by the mechanism mood test under DEC-NODE-FAMILIES, with high confidence after a second opinion: it can be violated: a counterexample would be fixed in the world, not in this node. Noted for a later split: EVIDENCE paragraph: 'At least three places currently assert human-only outright ... None of them cite DEC-FP-ACCEPT-AUTHORITY and none is edged to it' -- a dated finding used as the test case, separable from the rule. The UID keeps its prefix: DEC-UID-OUTLIVES-TYPE.
<<<
RELATIONS:
- TYPE: Parent
  VALUE: MECH-BACKLOG-STRICTDOC-TOOLING
  ROLE: Backlogged_In
