[DOCUMENT]
TITLE: Each plan carries its own backlog document, and no new node type

[GRAMMAR]
IMPORT_FROM_FILE: @repo

[DECISION]
UID: DEC-PLAN-SCOPED-BACKLOG
TITLE: Each plan carries its own backlog document, and no new node type
AUTHORED_BY: human
STATUS: superseded
RETIRES_ON: >>>
An item needs to be tracked while living outside its plan's backlog document,
at which point an explicit register node and a Backlogged_In role become the
cheaper answer.
<<<
STATEMENT: >>>
Every plan directory may hold a 99-backlog document. Anything noticed but not
groomed goes there as an ordinary node. Grooming means moving the node into a
numbered document in the same plan; the UID never changes, so nothing that
cites it breaks.

The plan's ungroomed set is therefore the contents of that document. Debt
remaining when a plan closes is whatever is still there, and what to do with
it is not decided here.
<<<
RATIONALE: >>>
A dedicated BACKLOG node type was considered and rejected. The existing types
already say what kind of work an item is -- a MECHANISM to build, a DECISION to
make, a SPIKE to run -- and a separate type would throw that away and need
mapping back on grooming. Containment by document needs no grammar change at
all.
<<<
COMMENT: >>>
Deliberately not solved here: a repo-level backlog above plans. That decision
waits for a plan to actually close with debt on it.
<<<
RELATIONS:
- TYPE: Parent
  VALUE: DEC-BACKLOG-IS-A-REGISTER-NODE
  ROLE: Superseded_By
