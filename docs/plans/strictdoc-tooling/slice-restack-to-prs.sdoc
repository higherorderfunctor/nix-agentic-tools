[DOCUMENT]
TITLE: Restack the long-lived branch into reviewable pull requests

[GRAMMAR]
IMPORT_FROM_FILE: @repo

[WORK]
UID: SLICE-RESTACK-TO-PRS
TITLE: Restack the long-lived branch into reviewable pull requests
AUTHORED_BY: human
STATEMENT: >>>
Cut the accumulated branch into a series of pull requests ordered so each is
independently reviewable, and land them.
<<<
RATIONALE: >>>
Slotted as future work so the strategy is tracked rather than remembered. Not
groomed: the cut points depend on what has accumulated by the milestone.
<<<
COMMENT: >>>
Retyped from SLICE to WORK on 2026-08-30 under DEC-SLICE-DECOMPOSES-TO-WORK and DEC-NODE-FAMILIES. The UID keeps its retired prefix: DEC-UID-OUTLIVES-TYPE.
<<<
RELATIONS:
- TYPE: Parent
  VALUE: DEC-LONG-LIVED-BRANCH
  ROLE: Governed_By
- TYPE: Parent
  VALUE: MECH-BACKLOG-STRICTDOC-TOOLING
  ROLE: Backlogged_In
