[DOCUMENT]
TITLE: Take strictdoc from upstream's own flake instead of our overlay

[GRAMMAR]
IMPORT_FROM_FILE: @repo

[MECHANISM]
UID: MECH-STRICTDOC-UPSTREAM-FLAKE
TITLE: Take strictdoc from upstream's own flake instead of our overlay
AUTHORED_BY: llm
STATEMENT: >>>
strictdoc ships a flake. Cut over to it and retire the overlay written as step
zero of this plan.

The operator has accepted the consequence: an upstream flake tracks main rather
than releases, which is a change from the release-tracking the overlay was built
for and is normal practice. Worth watching rather than worth avoiding.

Check on the way through whether the two dependency adjustments the overlay
carries -- the newer reqif and the relaxed pygments pin -- are still needed, and
whether cache-hit parity survives, since an upstream flake brings its own lock.
<<<
RATIONALE: >>>
The overlay existed because nobody had checked for a flake. Keeping a
first-party override alongside an upstream one is two things to maintain for
one package.
<<<
COMMENT: >>>
Implemented 2026-08-27. overlays/dev-tools/strictdoc.nix re-exports
inputs.strictdoc.packages.<system>.default unchanged, on the same plain-attrset-
update contract as overlays/semble.nix, so pkgs.ai.devTools.strictdoc keeps its
attribute path and its store path is byte-identical to a direct build of the
upstream flake. No consumer that takes the package from that seam changed.

Both questions the statement asked, answered. The dependency adjustments are
DEAD, not merely unneeded: upstream's flake is a uv2nix set built from the
repository's own uv.lock, which pins every dependency to the artifact the
release was tested against, so nothing resolves reqif or pygments against a
nixpkgs pin any more. Cache-hit parity SURVIVES and now holds trivially -- the
derivation closes over upstream's locked nixpkgs, so no consumer pin can move
it -- and the row was kept because a row that passes structurally is still what
catches a later final-bound wrapper.

The main-tracking consequence did not bite. Main was byte-identical to release
0.28.3 when the input was added (same tarball narHash), it built clean, and the
binary reports 0.28.3. The pre-approved contingency of pinning refs/tags/<rel>
was not used.

Two things this cost, both logged rather than fixed here. The version assertion
is gone -- MECH-STRICTDOC-VERSION-SMOKE. And SLICE-STRICTDOC-OVERLAY's STATEMENT
now specifies a build that does not exist ("a thin override of the nixpkgs
derivation ... from a sidecar, with the two dependency adjustments"); only its
COMMENT record the change. Whether that statement is rewritten or the slice is
closed and superseded is a contract question and so the operator's, not an
implementing session's. RULED 2026-08-27: rewritten in place, because
superseding is not expressible for a slice -- `Superseded_By` is declared only
on DECISION. That statement now describes the shipped shape, and the missing
transition is logged as MECH-SLICE-CANNOT-BE-SUPERSEDED.

One consumer DID have to change, and it is the one that never went through the
seam. overlays/dev-tools/strictdoc-grammar-extract.nix read the derivation's
internals: `.dependencies` (a nixpkgs list of derivations) and
$out/<sitePackages>. Upstream's package is mkApplication over a virtual
environment, so $out holds bin/strictdoc and nothing else, and `dependencies`
is a uv2nix name-to-extras ATTRSET -- the splice throws at eval rather than
mis-resolving. It now wraps the venv interpreter named by that script's shebang,
which is the only handle on the venv since it is not a flake output, with
ast_grep_py added to PYTHONPATH from ourPkgs. MEASURED: upstream 3.14.6 against
ourPkgs 3.14.7, ast_grep_py imports clean, and the grammar builder returns the
same 4adcdb05... grammar the implementation brief records. That splice is a
minor-version coupling and the package's existing installCheckPhase is what
makes a future divergence fail at build time.

Written before the wrapper moved: it left overlays/ entirely later the same day
and is packages/strictdoc-grammar/lib/mkExtract.nix, so the path named above no
longer exists and its ourPkgs is now the consumer's pkgs. The splice, the
measurement and the coupling are unchanged -- see
MECH-GRAMMAR-EXTRACT-SOURCE-BOUNDARY.
<<<
