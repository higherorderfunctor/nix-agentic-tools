[DOCUMENT]
TITLE: A create is a pure in-memory proposal, dry run or not

[GRAMMAR]
IMPORT_FROM_FILE: @repo

[MECHANISM]
UID: MECH-SCRIBE-NEW-TOUCHES-DISK-UNDER-DRY-RUN
TITLE: A create is a pure in-memory proposal, dry run or not
AUTHORED_BY: llm
STATEMENT: >>>
A create is a pure in-memory proposal. The document is built in memory, joins
pending() like every other edit, and reaches the disk only in save(): under
--dry-run the whole new file prints as an addition and nothing is written, and
a refused create leaves no skeleton behind. A joint fired "before the write"
on `new` can therefore be taken at its word.

How the document is built without a reload is
[LINK: MECH-SCRIBE-NEW-BUILDS-THE-DOCUMENT].

THIS NODE RECORDS A DEFECT THAT IS NOW FIXED, and is kept rather than deleted
([LINK: DEC-NO-DELETES-YET]). Until 2026-09-01 `scribe new` wrote a
header-only skeleton to DISK and reloaded the canon before the node was
validated, under --dry-run too, where the skeleton was unlinked again at the
end of the run. Measured 2026-08-28 while inventorying scribe's phases for the
hook layer, which is what it was filed against.
<<<
