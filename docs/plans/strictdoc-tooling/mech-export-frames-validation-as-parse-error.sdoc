[DOCUMENT]
TITLE: strictdoc export reports a semantic rejection as "could not parse file"

[GRAMMAR]
IMPORT_FROM_FILE: @repo

[MECHANISM]
UID: MECH-EXPORT-FRAMES-VALIDATION-AS-PARSE-ERROR
TITLE: strictdoc export reports a semantic rejection as "could not parse file"
AUTHORED_BY: llm
STATEMENT: >>>
Measured on 0.28.3 while wiring checks/strictdoc-grammar-negative-fixtures.nix.
A grammar that violates an SDocValidator rule -- REVERSE_ROLE without ROLE,
SECTION not composite, TEXT composite -- is rejected during the step strictdoc
prints as `Build traceability graph`, well after `Reading SDOC` reports the
same file read successfully. The first line of the diagnostic is nevertheless:

  error: could not parse file: g.sgra.
  Semantic error: Grammar element 'NOTE' defines REVERSE_ROLE without ROLE ...

So the headline names the wrong layer, and the line that names the right one is
below it. Anything classifying a rejection by matching the error TEXT will read
every semantic failure as a parse failure -- and a fixture asserting "rejected
at the parse" would pass while proving nothing about the parser.

The layer is still distinguishable, just not from the message: a bare
SDocGrammarReader.read of the .sgra accepts all three, and only the whole-corpus
export rejects them. That is what the check discriminates on.
<<<
RATIONALE: >>>
Worth recording because the misleading half is the part a reader sees first, and
because it makes the obvious implementation of a layer assertion silently wrong
rather than loudly wrong.
<<<
RELATIONS:
- TYPE: Parent
  VALUE: MECH-BACKLOG-STRICTDOC-TOOLING
  ROLE: Backlogged_In
