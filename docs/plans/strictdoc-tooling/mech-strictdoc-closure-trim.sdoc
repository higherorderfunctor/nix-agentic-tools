[DOCUMENT]
TITLE: Drop the three strictdoc dependencies that cost closure and are unused

[GRAMMAR]
IMPORT_FROM_FILE: @repo

[EVIDENCE]
UID: MECH-STRICTDOC-CLOSURE-TRIM
TITLE: Drop the three strictdoc dependencies that cost closure and are unused
AUTHORED_BY: llm
STATEMENT: >>>
SPIKE-EXECUTABLE-RULES measured six dependencies in nixpkgs' strictdoc
expression that upstream's pyproject.toml does not declare. Three of them --
graphviz, pybtex and setuptools -- cost closure; the other three return
through html2pdf4doc, so removing them buys nothing. Removing the three is a
`dependencies` filter in overlays/dev-tools/strictdoc.nix.

Deliberately NOT done as part of SLICE-STRICTDOC-OVERLAY, whose shape is a
thin override that leaves the dependency set upstream-owned. Trimming it is a
separate, arguable change: it makes this package diverge from nixpkgs in a way
a version bump cannot re-converge, and the win is closure size on a package
every session already has.
<<<
RATIONALE: >>>
Recorded so the measurement is not re-run. If it is picked up, verify the
six-and-three split against the release in the sidecar rather than trusting
this node -- it was measured against 0.27.1 and the dependency list moved in
0.28.
<<<
COMMENT: >>>
CHANGED SHAPE 2026-08-27, by MECH-STRICTDOC-UPSTREAM-FLAKE, and there is no
sidecar to verify against any more. The measurement was taken against nixpkgs'
strictdoc expression, and this repository no longer builds from it: the package
is upstream's own uv2nix build from their uv.lock. There is no `dependencies`
filter to apply and no first-party override to hang one on, so the six-and-three
split describes a derivation nothing here evaluates.

If closure size is still worth chasing it is now a question for upstream's own
flake, which puts it outside this repository and probably outside this plan.

Retyped from MECHANISM to EVIDENCE on 2026-08-30 by the mechanism mood test under DEC-NODE-FAMILIES, with medium confidence after a second opinion: it records what was observed once, not how something always behaves. Noted for a later split: The proposal half ('Removing the three is a dependencies filter in overlays/dev-tools/strictdoc.nix'; deliberately not done in SLICE-STRICTDOC-OVERLAY) is work, declared dead by COMMENT after MECH-STRICTDOC-UPSTREAM-FLAKE; splitting would leave the six-and-three measurement as EVIDENCE and retire the proposal. The UID keeps its prefix: DEC-UID-OUTLIVES-TYPE.
<<<
RELATIONS:
- TYPE: Parent
  VALUE: MECH-BACKLOG-STRICTDOC-TOOLING
  ROLE: Backlogged_In
