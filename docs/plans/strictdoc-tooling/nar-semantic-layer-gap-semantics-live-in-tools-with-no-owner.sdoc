[DOCUMENT]
TITLE: Semantics still live in tools with no owner

[GRAMMAR]
IMPORT_FROM_FILE: @repo

[NARRATIVE]
UID: NAR-SEMANTIC-LAYER-GAP-SEMANTICS-LIVE-IN-TOOLS-WITH-NO-OWNER
TITLE: Semantics still live in tools with no owner
AUTHORED_BY: llm
WIDGET: prose
PLACE: screen
STATEMENT: >>>
The fingerprint ripple, the signing rules, the plan-reference check and the layout rules are all semantic-layer rules written in Python. The node that records the misplacement has its judgement deliberately pending and no work node. And the lane rule — the one thing the ruling that decomposed SLICE into work ([LINK: DEC-SLICE-DECOMPOSES-TO-WORK]) gained — has no layer information to check against.

> Semantics still live in tools with no owner: fp-check ripple, fp-accept rules, MECH-PLAN-REFS-CHECK and the layout rules are all L3 rules in Python (MECH-MILESTONE-TWO-SEMANTICS-MISPLACED pending, no WORK node), and DEC-DEFER-LAYER leaves the lane rule -- the one thing DEC-SLICE-DECOMPOSES-TO-WORK gained -- with no LAYER input to check against.
<<<
PARENT_FP: >>>
DEC-DEFER-LAYER:0000000
DEC-LAYER-STACK:0000000
DEC-SLICE-DECOMPOSES-TO-WORK:0000000
MECH-MILESTONE-TWO-SEMANTICS-MISPLACED:0000000
MECH-PLAN-REFS-CHECK:0000000
MECH-SDOC-LAYOUT-CHECK:0000000
MECH-SDOC-VOCABULARY-SINGLE-SOURCE:0000000
<<<
RELATIONS:
- TYPE: Parent
  VALUE: DEC-SLICE-DECOMPOSES-TO-WORK
  ROLE: Cites
- TYPE: Parent
  VALUE: DEC-LAYER-STACK
  ROLE: Cites
- TYPE: Parent
  VALUE: MECH-MILESTONE-TWO-SEMANTICS-MISPLACED
  ROLE: Cites
- TYPE: Parent
  VALUE: MECH-PLAN-REFS-CHECK
  ROLE: Cites
- TYPE: Parent
  VALUE: MECH-SDOC-LAYOUT-CHECK
  ROLE: Cites
- TYPE: Parent
  VALUE: MECH-SDOC-VOCABULARY-SINGLE-SOURCE
  ROLE: Cites
- TYPE: Parent
  VALUE: DEC-DEFER-LAYER
  ROLE: Cites
