[DOCUMENT]
TITLE: Files, plans and how long a node lives

[GRAMMAR]
IMPORT_FROM_FILE: @repo

[NARRATIVE]
UID: NAR-SEMANTIC-LAYER-FILES-AND-RETENTION
TITLE: Files, plans and how long a node lives
AUTHORED_BY: llm
WIDGET: rows
PLACE: screen
STATEMENT: >>>
One node per file; retention keyed on directory; plans, backlogs, beads and ownership.

- One node per file, named for its UID in lowercase, with the document title equal to the node title, in flat plan directories. All 202 names hold; one title mismatches. Applied, but not yet ratified.
[LINK: DEC-NODE-FILE-NAMING]
> one node per file; basename = UID lowercased; document TITLE = node TITLE; flat plan dirs; 202/202 names hold, 1 title mismatch [OPEN: DEC-NODE-FILE-NAMING]
- How long a node lives is decided by where its file sits, not by its type: plan nodes are collectable (190), spec nodes are durable (8), and nodes beside a package move with that package (4).
[LINK: NAR-SEMANTIC-LAYER-GAP-MEMBERSHIP-AND-COLLECTION-CONTRADICT]
> three retention classes keyed on FILE not type: docs/plans/<P>/ collectable (190); docs/spec/ durable (8); packages/*/.sdoc/ moves with package (4) [WORKS]
- Whether spec nodes and package-side nodes are one durable class or two ranked ones — and whether architecture may depend on the spec — is unsaid. One plan-to-spec edge exists; no architecture-to-spec edges.
> spec vs .sdoc: one durable class or two ranked (may arch depend on spec?); 1 plan->spec edge, 0 arch<->spec [UNADDRESSED]
- No rule says what collects a plan, when, or how a node is promoted out of one. The lean: supersede first, collect later, never delete.
[LINK: DEC-PLAN-LIFECYCLE-OPEN] [LINK: NAR-SEMANTIC-LAYER-TYPE-DECISION] [LINK: NAR-SEMANTIC-LAYER-TYPE-WORK] [LINK: NAR-SEMANTIC-LAYER-GAP-MEMBERSHIP-AND-COLLECTION-CONTRADICT]
> plan retention (what collects a plan, when) and promotion out of a plan: no rule; lean = supersede first, collect later, no deletes [OPEN: DEC-PLAN-LIFECYCLE-OPEN]
- A node belongs to a plan by sitting in its directory. The one-grammar ruling says membership is already a relation — but 112 groomed plan nodes carry no such edge, so there is nothing to remove when a plan dissolves.
[LINK: DEC-ONE-GRAMMAR] [LINK: NAR-SEMANTIC-LAYER-GAP-MEMBERSHIP-AND-COLLECTION-CONTRADICT]
> plan membership = directory; DEC-ONE-GRAMMAR says "already a relation", but 112 groomed plan nodes carry no plan edge to remove [GAP]
- Settled architecture lives in a directory beside the code it describes, each node linked to a file. That placement retires when a tool can extract the same content from source comments.
[LINK: DEC-ARCH-COLOCATION] [LINK: NAR-SEMANTIC-LAYER-TYPE-MECHANISM]
> settled architecture beside code, each node File-linked; retires when a source-comment extractor exists [OPEN: DEC-ARCH-COLOCATION]
- A plan's backlog is one register node; ungroomed items point at it. Grooming drops that edge; the UID never changes. Who may groom is unstated.
[LINK: NAR-SEMANTIC-LAYER-TYPE-MECHANISM] [LINK: NAR-SEMANTIC-LAYER-GAP-IDENTITY-HAS-NO-CARRIER]
> backlog = register node per plan; items carry Backlogged_In; grooming drops the edge, UID unchanged; which class may groom: unstated [WORKS]
- Beads is the agent's private working store, one per identity. Canon and beads differ in authority, not shape. From the moment a plan is handed over, execution state — done, who holds it, what blocks it — lives in beads.
[LINK: NAR-SEMANTIC-LAYER-TYPE-WORK]
> beads = LLM's private working graph, one store per identity; canon vs beads = authority, not shape; execution state (done? holder? blocker?) lives in beads from ingest (handover) [WORKS]
- One human owns a plan (though it is recorded nowhere); work can involve many identities; handover freezes the scope handed over, not the whole plan; and an agent may file backlog nodes without asking.
[LINK: NAR-SEMANTIC-LAYER-TYPE-WORK]
> one identity:human owns a plan (recorded nowhere); WORK is multi-identity; ingest freezes the handed-over scope, not the plan; identity:llm may file backlog nodes unasked [WORKS]
- An agent's key is a second writer on every plan, but the difference between an owner and a delegate is unwritten. The retirement condition 'two people edit one plan' can be read more than one way, and nothing says which.
[LINK: NAR-SEMANTIC-LAYER-GAP-IDENTITY-HAS-NO-CARRIER]
> split: an identity:llm key is a second writer on every plan; owner vs delegate unwritten; RETIRES_ON "two people edit one plan" ambiguous [GAP]
<<<
PARENT_FP: >>>
DEC-ARCH-COLOCATION:0000000
DEC-NODE-FILE-NAMING:0000000
DEC-ONE-GRAMMAR:0000000
DEC-PLAN-LIFECYCLE-OPEN:0000000
NAR-SEMANTIC-LAYER-GAP-IDENTITY-HAS-NO-CARRIER:0000000
NAR-SEMANTIC-LAYER-GAP-MEMBERSHIP-AND-COLLECTION-CONTRADICT:0000000
NAR-SEMANTIC-LAYER-TYPE-DECISION:0000000
NAR-SEMANTIC-LAYER-TYPE-MECHANISM:0000000
NAR-SEMANTIC-LAYER-TYPE-WORK:0000000
NAR-TERM-BEADS:0000000
NAR-TERM-CANON:0000000
<<<
RELATIONS:
- TYPE: Parent
  VALUE: DEC-NODE-FILE-NAMING
  ROLE: Cites
- TYPE: Parent
  VALUE: NAR-SEMANTIC-LAYER-GAP-MEMBERSHIP-AND-COLLECTION-CONTRADICT
  ROLE: Cites
- TYPE: Parent
  VALUE: DEC-PLAN-LIFECYCLE-OPEN
  ROLE: Cites
- TYPE: Parent
  VALUE: NAR-SEMANTIC-LAYER-TYPE-DECISION
  ROLE: Cites
- TYPE: Parent
  VALUE: NAR-SEMANTIC-LAYER-TYPE-WORK
  ROLE: Cites
- TYPE: Parent
  VALUE: DEC-ONE-GRAMMAR
  ROLE: Cites
- TYPE: Parent
  VALUE: DEC-ARCH-COLOCATION
  ROLE: Cites
- TYPE: Parent
  VALUE: NAR-SEMANTIC-LAYER-TYPE-MECHANISM
  ROLE: Cites
- TYPE: Parent
  VALUE: NAR-SEMANTIC-LAYER-GAP-IDENTITY-HAS-NO-CARRIER
  ROLE: Cites
- TYPE: Parent
  VALUE: NAR-TERM-CANON
  ROLE: Cites
- TYPE: Parent
  VALUE: NAR-TERM-BEADS
  ROLE: Cites
