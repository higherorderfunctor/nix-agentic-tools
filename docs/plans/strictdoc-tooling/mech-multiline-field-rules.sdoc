[DOCUMENT]
TITLE: Which fields may carry block values belongs to the writing tool

[GRAMMAR]
IMPORT_FROM_FILE: @repo

[MECHANISM]
UID: MECH-MULTILINE-FIELD-RULES
TITLE: Which fields may carry block values belongs to the writing tool
AUTHORED_BY: llm
STATEMENT: >>>
A field's value is written either inline or as a block delimited by the
triple-angle markers, and strictdoc decides which from three things at once:
reserved single-line names are never blocks; otherwise position decides, with
everything after TITLE or STATEMENT being a block; and non-string types are
never blocks.

That is document-writing behaviour, not grammar declaration, so it belongs to
the milestone that makes a tool the only writer of sdoc files rather than to
the grammar surface. Recorded here explicitly UNSETTLED at the operator's
instruction, to be picked up there rather than rediscovered.
<<<
RATIONALE: >>>
It surfaced during the grammar milestone and was nearly settled in the wrong
place. A rule about how values are written cannot be enforced by a surface that
only declares what fields exist.
<<<
RELATIONS:
- TYPE: Parent
  VALUE: MECH-BACKLOG-STRICTDOC-TOOLING
  ROLE: Backlogged_In
