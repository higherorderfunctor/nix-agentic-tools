[DOCUMENT]
TITLE: Identity has no carrier

[GRAMMAR]
IMPORT_FROM_FILE: @repo

[NARRATIVE]
UID: NAR-SEMANTIC-LAYER-GAP-IDENTITY-HAS-NO-CARRIER
TITLE: Identity has no carrier
AUTHORED_BY: llm
WIDGET: prose
PLACE: screen
STATEMENT: >>>
Every rule about who may do something — sign a contract, raise authorship, accept a decision, groom, delete — needs to know who is acting. The three things that would tell it (the hook layer's actor slot — the field in a handler's payload that would say who is acting; the table mapping keys to human-or-agent; and the guard that reads it) are unbuilt and nobody owns them. Meanwhile about ten rulings, and the acceptance flow itself, already carry human authority under an agent's key.

> Identity has no carrier: the L2 actor slot, the key->class table and its guard are unbuilt and unowned, so every authority rule (sign, flip AUTHORED_BY, accept a DECISION, groom, delete) has nothing to read; ~10 relayed rulings and the accept flow already write human authority under an llm key.
<<<
PARENT_FP: >>>
DEC-FP-ACCEPT-AUTHORITY:0000000
DEC-NO-DELETES-YET:0000000
MECH-HOOK-MIDDLEWARE-INTERFACE:0000000
SLICE-HOOK-LAYER:0000000
<<<
RELATIONS:
- TYPE: Parent
  VALUE: MECH-HOOK-MIDDLEWARE-INTERFACE
  ROLE: Cites
- TYPE: Parent
  VALUE: DEC-FP-ACCEPT-AUTHORITY
  ROLE: Cites
- TYPE: Parent
  VALUE: DEC-NO-DELETES-YET
  ROLE: Cites
- TYPE: Parent
  VALUE: SLICE-HOOK-LAYER
  ROLE: Cites
