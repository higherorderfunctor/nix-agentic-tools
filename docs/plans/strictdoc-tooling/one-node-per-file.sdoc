[DOCUMENT]
TITLE: One node per file

[GRAMMAR]
IMPORT_FROM_FILE: @repo

[MECHANISM]
UID: MECH-ONE-NODE-PER-FILE
TITLE: One node per file, because an agent reads files and traverses edges
DEPTH: sketch
AUTHORED_BY: llm
STATEMENT: >>>
A file holds exactly one node. One requirement, one plan step, one plan, one
milestone, one backlog item, one decision -- one. The operator's word for it is
ONE.

Measured 2026-08-27, and the ratio is the whole argument. The corpus is 421 KB
across 156 nodes in 8 files, so an average node is about 2.7 KB. Reading one
node out of 99-backlog.sdoc costs 279 KB, because that file holds 110 of them.
Reading one out of 03-executable-rules.sdoc costs 74 KB for 7 nodes, 10.5 KB
apiece. An agent that opens the backlog to read one item takes the entire
backlog into context, roughly a hundred times what it came for, and does it
again on every re-read.

The graph is a web pulled in by edges, not a set of documents read whole. That
only works if the unit a reader fetches is the unit the graph addresses. Today
the addressable unit is a node and the fetchable unit is a file, and the two are
off by two orders of magnitude.

Migration is mechanical -- the UID never changes, so nothing citing a node
breaks when it moves -- but it is 156 files and it wants the writing tool from
SLICE-SDOC-CLI so the split is done by something that validates, not by hand.
99-backlog.sdoc is the first target and 03-executable-rules.sdoc the second.

The naming and directory convention for 156 single-node files is NOT settled
here. Nor is what happens to the numbered-document convention, or to the
per-plan 99-backlog.sdoc, which becomes a query over a directory rather than a
file.
<<<
RATIONALE: >>>
This is a context-economy defect before it is a tidiness one, and the system's
stated purpose makes it acute: DEC-SYSTEM-PURPOSE optimizes for a reader with a
bounded context and no memory of yesterday. A layout that forces that reader to
take 279 KB to learn 2.7 KB is working against the thing the graph is for.

It also compounds silently. Every session that files a backlog item makes the
next session's read more expensive, and nothing reports the cost.

The operator expects this to get clearer once semantics land and each item type
can have its own grammar, which is when a file's shape and its single node's
type become the same statement.
<<<
NOTES: >>>
Raised by the operator 2026-08-27 after reading the file sizes: "thats a failure
mode ... 273k backlog loaded into context churning with re-reads ... you are
supposed to pull in from the graph what you need from edges."

Deferred deliberately to a later session; recorded here so it is not
rediscovered from the file listing a third time.

This session made it worse before recording it: sixteen consolidated backlog
nodes were appended to 99-backlog.sdoc rather than given files, which is roughly
40 KB added to the file this node exists to break up.

Adjacent but different: MECH-GROOMED-NODES-STAY-IN-THE-BACKLOG-FILE is about
groomed nodes not moving to a numbered document. That is a question of WHICH
file; this is a question of how many nodes a file may hold. Under this rule the
other node's problem largely dissolves, since a groomed node moves by being one
file rather than by being cut out of one.

Tool reads are a separate lever and are not in scope here. The operator's words:
"we can tune later to not have as many tool reads, but for now thats a failure
mode."
<<<
