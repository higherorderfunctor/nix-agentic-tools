[DOCUMENT]
TITLE: Not placed anywhere yet

[GRAMMAR]
IMPORT_FROM_FILE: @repo

[NARRATIVE]
UID: NAR-SEMANTIC-LAYER-UNPLACED
TITLE: Not placed anywhere yet
AUTHORED_BY: llm
WIDGET: rows
PLACE: screen
STATEMENT: >>>
Four nodes the sheet could not file under a topic.

- The line between flake checks and devenv tasks is undrawn; five grammar checks are written twice; neither system is a joint.
[LINK: MECH-CHECK-SYSTEM-BOUNDARY] [LINK: NAR-SEMANTIC-LAYER-TYPE-MECHANISM]
> MECH-CHECK-SYSTEM-BOUNDARY: flake checks vs devenv tasks; 5 grammar arms written twice; neither is a joint [UNADDRESSED]
- Two known problems — vocabularies copied three times over in Python, and milestone two's rules sitting in the tool (a judgement still pending) — have no owner and no work node.
[LINK: MECH-MILESTONE-TWO-SEMANTICS-MISPLACED] [LINK: MECH-SDOC-VOCABULARY-SINGLE-SOURCE] [LINK: NAR-SEMANTIC-LAYER-TYPE-MECHANISM] [LINK: NAR-SEMANTIC-LAYER-GAP-SEMANTICS-LIVE-IN-TOOLS-WITH-NO-OWNER]
> MECH-SDOC-VOCABULARY-SINGLE-SOURCE (node discovery, placeholder and PARENT_FP parsing duplicated in Python) and MECH-MILESTONE-TWO-SEMANTICS-MISPLACED (judgement PENDING): no owner, no WORK node [GAP]
- The mechanism that was to draw the boundary between defining semantics and this system's own semantics is dissolved — the layer stack draws it. The edge from code to its layer is still unplaced.
[LINK: DEC-LAYER-STACK] [LINK: MECH-SEMANTICS-DEFINITION-BOUNDARY] [LINK: NAR-SEMANTIC-LAYER-TYPE-MECHANISM] [LINK: NAR-SEMANTIC-LAYER-GAP-SEMANTICS-LIVE-IN-TOOLS-WITH-NO-OWNER]
> MECH-SEMANTICS-DEFINITION-BOUNDARY [FALLS OUT: DEC-LAYER-STACK draws it; code -> layer edge unplaced]
- The executable-rules probe has run and is the evidence behind the roadmap decision. Its retirement condition is unmet.
[LINK: DEC-EXECUTABLE-RULES-ROADMAP] [LINK: SPIKE-EXECUTABLE-RULES] [LINK: NAR-SEMANTIC-LAYER-TYPE-EVIDENCE] [LINK: NAR-SEMANTIC-LAYER-TYPE-DECISION]
> SPIKE-EXECUTABLE-RULES: run; the evidence behind DEC-EXECUTABLE-RULES-ROADMAP; RETIRES_ON unmet [WORKS]
<<<
PARENT_FP: >>>
DEC-EXECUTABLE-RULES-ROADMAP:0000000
DEC-LAYER-STACK:0000000
MECH-CHECK-SYSTEM-BOUNDARY:0000000
MECH-MILESTONE-TWO-SEMANTICS-MISPLACED:0000000
MECH-SDOC-VOCABULARY-SINGLE-SOURCE:0000000
MECH-SEMANTICS-DEFINITION-BOUNDARY:0000000
NAR-SEMANTIC-LAYER-GAP-SEMANTICS-LIVE-IN-TOOLS-WITH-NO-OWNER:0000000
NAR-SEMANTIC-LAYER-TYPE-DECISION:0000000
NAR-SEMANTIC-LAYER-TYPE-EVIDENCE:0000000
NAR-SEMANTIC-LAYER-TYPE-MECHANISM:0000000
NAR-TERM-JOINT:0000000
SPIKE-EXECUTABLE-RULES:0000000
<<<
RELATIONS:
- TYPE: Parent
  VALUE: MECH-CHECK-SYSTEM-BOUNDARY
  ROLE: Cites
- TYPE: Parent
  VALUE: NAR-SEMANTIC-LAYER-TYPE-MECHANISM
  ROLE: Cites
- TYPE: Parent
  VALUE: MECH-MILESTONE-TWO-SEMANTICS-MISPLACED
  ROLE: Cites
- TYPE: Parent
  VALUE: MECH-SDOC-VOCABULARY-SINGLE-SOURCE
  ROLE: Cites
- TYPE: Parent
  VALUE: NAR-SEMANTIC-LAYER-GAP-SEMANTICS-LIVE-IN-TOOLS-WITH-NO-OWNER
  ROLE: Cites
- TYPE: Parent
  VALUE: DEC-LAYER-STACK
  ROLE: Cites
- TYPE: Parent
  VALUE: MECH-SEMANTICS-DEFINITION-BOUNDARY
  ROLE: Cites
- TYPE: Parent
  VALUE: DEC-EXECUTABLE-RULES-ROADMAP
  ROLE: Cites
- TYPE: Parent
  VALUE: SPIKE-EXECUTABLE-RULES
  ROLE: Cites
- TYPE: Parent
  VALUE: NAR-SEMANTIC-LAYER-TYPE-EVIDENCE
  ROLE: Cites
- TYPE: Parent
  VALUE: NAR-SEMANTIC-LAYER-TYPE-DECISION
  ROLE: Cites
- TYPE: Parent
  VALUE: NAR-TERM-JOINT
  ROLE: Cites
