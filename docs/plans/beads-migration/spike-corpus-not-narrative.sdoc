[DOCUMENT]
TITLE: The corpus is 14 percent prose

[GRAMMAR]
IMPORT_FROM_FILE: @repo

[EVIDENCE]
UID: SPIKE-CORPUS-NOT-NARRATIVE
TITLE: The corpus is 14 percent prose
AUTHORED_BY: llm
STATEMENT: >>>
Across 42 files and 4252 lines: 23.9 percent blank, 16.2 percent tables, 14.3
percent prose, 12.1 percent rule blockquotes, 11.5 percent frontmatter, 10.4
percent code blocks, 8.8 percent presentation markup, 2.9 percent headings.
<<<
RATIONALE: >>>
Too narrative to convert is not an available objection.
<<<
COMMENT: >>>
Retyped from SPIKE to EVIDENCE on 2026-08-30: a probe is work, then evidence, then a decision (MECH-SPIKE-IS-A-PIPELINE-TO-A-DECISION; DEC-NODE-FAMILIES). Its STATUS was 'run'. Its RETIRES_ON read: Converted. The UID keeps its retired prefix: DEC-UID-OUTLIVES-TYPE.
<<<
