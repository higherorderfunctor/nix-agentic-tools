[DOCUMENT]
TITLE: Measured state of the fleet design corpus

[GRAMMAR]
IMPORT_FROM_FILE: @repo

[SPIKE]
UID: SPIKE-CORPUS-LINK-ROT
TITLE: Link rot in the source corpus
DEPTH: interface-settled
AUTHORED_BY: llm
STATUS: run
RETIRES_ON: >>>
The corpus is converted, after which dangling references are export errors
rather than a measurement.
<<<
STATEMENT: >>>
212 of 865 internal links dangle, 25 percent. 49 of 90 distinct targets resolve
to nothing. The split is 123 references across 9 dropped sections, 80 references
to register-row anchors that markdown cannot address below file granularity, and
9 to symbol anchors. One provenance row cites a dropped section in the very row
recording that it was dropped.
<<<
RATIONALE: >>>
This is the failure StrictDoc fails closed on. No hypothesis is needed about
whether validation helps here.
<<<

[SPIKE]
UID: SPIKE-CORPUS-SYMBOL-LAYER
TITLE: The symbol reference layer is healthy
DEPTH: interface-settled
AUTHORED_BY: llm
STATUS: run
RETIRES_ON: >>>
Converted, at which point symbol references become UIDs.
<<<
STATEMENT: >>>
60 of 61 symbol references resolve. The layer that rotted is the coarse
file-level anchor layer, not the fine mechanism-level one.
<<<
RATIONALE: >>>
UIDs at mechanism granularity were already invented by the author and that layer
works. The sdoc UID model is a fit arrived at independently, not an imposition.
<<<

[SPIKE]
UID: SPIKE-CORPUS-NOT-NARRATIVE
TITLE: The corpus is 14 percent prose
DEPTH: interface-settled
AUTHORED_BY: llm
STATUS: run
RETIRES_ON: >>>
Converted.
<<<
STATEMENT: >>>
Across 42 files and 4252 lines: 23.9 percent blank, 16.2 percent tables, 14.3
percent prose, 12.1 percent rule blockquotes, 11.5 percent frontmatter, 10.4
percent code blocks, 8.8 percent presentation markup, 2.9 percent headings.
<<<
RATIONALE: >>>
Too narrative to convert is not an available objection.
<<<

[INVARIANT]
UID: INV-REGISTER-NOT-AUTHORITATIVE
TITLE: The register is not the source of truth it claims to be
DEPTH: interface-settled
AUTHORED_BY: llm
STATEMENT: >>>
Seven open-card identifiers appear in section bodies with no register row at
all. One of them states a hard blocker cited by four sections and therefore
carries no retirement condition. Two register rows named as pointer-only appear
as no card anywhere.
<<<
RATIONALE: >>>
The register asserts that review state lives nowhere else. It does. Any
conversion that trusts the register as the complete decision set will silently
drop seven decisions.
<<<
PARENT_FP: DEC-CONVERT-IS-ADJUDICATION:0000000
RELATIONS:
- TYPE: Parent
  VALUE: DEC-CONVERT-IS-ADJUDICATION
  ROLE: Governed_By

[INVARIANT]
UID: INV-VOCABULARIES-UNBOUNDED
TITLE: Two declared-bounded vocabularies are unbounded in practice
DEPTH: interface-settled
AUTHORED_BY: llm
STATEMENT: >>>
The grain rule labels: 127 rules across 90 distinct labels, one placeholder
appearing 22 times, and case-variant duplicates. The corpus names this a blocker
for a typed model and leaves it open. The cast kind column: declared as ten
values, 43 observed, including multi-word phrases. Nothing in the corpus notices
the second one.
<<<
RATIONALE: >>>
Neither should become a SingleChoice on conversion. The grain vocabulary
dissolves entirely if rules bind to a mechanism by edge rather than by label.
<<<
PARENT_FP: DEC-CONVERT-IS-ADJUDICATION:0000000
RELATIONS:
- TYPE: Parent
  VALUE: DEC-CONVERT-IS-ADJUDICATION
  ROLE: Governed_By

[DECISION]
UID: DEC-SOURCE-OUT-OF-REPO
TITLE: The authoritative source of the fleet plan is outside this repository
AUTHORED_BY: llm
STATUS: open
RETIRES_ON: >>>
The corpus is converted to sdoc in this repository, or the operator confirms the
markdown carve-out supersedes the original entirely.
<<<
STATEMENT: >>>
The original plan exists as a published HTML artifact outside this repository.
The markdown under private/strict-doc/design is a carve-out from it, produced to
strip reader-facing duplication and prepare for sdoc conversion. Which of the
two is authoritative where they disagree has not been decided, and the carve-out
is not human signed off.
<<<
RATIONALE: >>>
Recorded as a node so that a conversion session does not silently pick one.
<<<
NOTES: >>>
Human acceptance needed. This node points at content this graph cannot validate.
<<<
