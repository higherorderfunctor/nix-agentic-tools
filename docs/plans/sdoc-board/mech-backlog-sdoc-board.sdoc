[DOCUMENT]
TITLE: The sdoc-board plan's backlog register

[GRAMMAR]
IMPORT_FROM_FILE: @repo

[MECHANISM]
UID: MECH-BACKLOG-SDOC-BOARD
TITLE: The sdoc-board plan's backlog register
DEPTH: interface-settled
AUTHORED_BY: llm
STATEMENT: >>>
The linchpin every ungroomed item in this plan points at. An item is in the backlog when it carries Backlogged_In to this node, and the plan's backlog is the inbound Backlogs set. This node holds no list; the edges are the list.
<<<
