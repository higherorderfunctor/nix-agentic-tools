[DOCUMENT]
TITLE: A write marks the graph dirty; the next read that needs it reconciles once

[GRAMMAR]
IMPORT_FROM_FILE: @repo

[DECISION]
UID: DEC-SCRIBE-DEFERS-THE-REBUILD
TITLE: A write marks the graph dirty; the next read that needs it reconciles once
AUTHORED_BY: llm
STATUS: superseded
RETIRES_ON: Reconciliation stops dominating the cost of a write batch, or strictdoc gains a document lifecycle primitive making an incremental path as safe as the rebuild.
STATEMENT: >>>
A write marks the workspace dirty rather than rebuilding the graph. The next
operation that needs a consistent whole-graph view reconciles once, so a run of
writes costs one rebuild instead of one each.

Each write still parses its OWN file immediately, which catches a document that
will not parse and names it at the write that caused it. What defers is the
cross-document check -- duplicate UIDs, dangling relation targets -- which needs
the graph and which one reconciliation answers for the whole batch.

Measured: ten new nodes then one read costs about 505 ms against roughly 30
seconds today, because sdoc new pays three full graph loads at about 0.95 s
each.

The steering is advisory, never load-bearing. A relation whose target was
created earlier in the same batch does not resolve yet, so the daemon
reconciles on a miss instead of erroring. Batching badly costs a rebuild that
would have been paid anyway; nothing breaks.
<<<
RATIONALE: >>>
Batching is what made the expensive choice cheap. Reconciling with strictdoc's
own documented rebuild costs about 500 ms, and a hand-built document-tree
insertion would cost about 25 ms -- but amortized over a batch the difference
stops mattering, so the plan takes the documented path and builds nothing that
reaches into DocumentTree's internals.
<<<
RELATIONS:
- TYPE: Parent
  VALUE: DEC-SCRIBE-DEFERRED-RELOAD-IS-FULL
  ROLE: Superseded_By
