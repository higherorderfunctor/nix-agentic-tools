[DOCUMENT]
TITLE: The scribe verbs do not go through the daemon yet

[GRAMMAR]
IMPORT_FROM_FILE: @repo

[MECHANISM]
UID: MECH-SCRIBE-VERB-PROXY
TITLE: The scribe verbs do not go through the daemon yet
DEPTH: sketch
AUTHORED_BY: llm
STATEMENT: >>>
The scribe verbs still load the graph in-process. Routing them through the
daemon is not a transport question: sdoc_cli's finish() calls verify(), a
full reload, which is precisely the cost the workspace's deferred
reconciliation replaces. So the verbs move only once their verification is
the workspace's rather than their own.

The shape is likely a single RPC carrying argv, dispatched server-side
against the held graph so no verb surface is duplicated -- main() already
takes a graph and a root as its only inputs.
<<<
RELATIONS:
- TYPE: Parent
  VALUE: MECH-BACKLOG-SCRIBE-DAEMON
  ROLE: Backlogged_In
- TYPE: Parent
  VALUE: MECH-SCRIBE-RPC
  ROLE: Assumes
