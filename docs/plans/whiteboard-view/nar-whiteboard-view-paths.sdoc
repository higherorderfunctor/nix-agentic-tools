[DOCUMENT]
TITLE: The paths that must work

[GRAMMAR]
IMPORT_FROM_FILE: @repo

[NARRATIVE]
UID: NAR-WHITEBOARD-VIEW-PATHS
TITLE: The paths that must work
AUTHORED_BY: llm
WIDGET: rows
PLACE: screen
STATEMENT: >>>
Seven use cases, each covered by the rulings and programs it points at with Covered_By. Each is designed; none has yet been walked end to end against the built programs and recorded as evidence.

- The operator chooses a different word for a ruled term, and every narrative that used it shows a drifted citation.
[LINK: UC-RENAME-A-TERM] [SETTLED]
- A ruling lands, the sections that cite it show drift, and only those are re-read, re-cut and re-signed.
[LINK: UC-RECUT-AFTER-A-RULING] [SETTLED]
- The view renders its own design from this root through the same programs, with no renderer change.
[LINK: UC-FLIP-THE-VIEW] [SETTLED]
- From a type, gap or node screen, a line's crumb lands on it among its topic neighbours with the filter kept.
[LINK: UC-FOLLOW-A-LINE-HOME] [SETTLED]
- With the whiteboard switched off, the page shows the claims, their edges, their ladders and the node index, as v1 did.
[LINK: UC-READ-THE-CANON-APART-FROM-THE-WHITEBOARD] [SETTLED]
- Switch systems on and off and watch the figures, counts and indexes follow without a reload; the address carries the selection.
[LINK: UC-TOGGLE-A-SYSTEM] [SETTLED]
- An author writes a new view with the scribe and gets a page without touching the renderer.
[LINK: UC-WRITE-A-VIEW-BY-HAND] [SETTLED]
<<<
PARENT_FP: >>>
UC-FLIP-THE-VIEW:0000000
UC-FOLLOW-A-LINE-HOME:0000000
UC-READ-THE-CANON-APART-FROM-THE-WHITEBOARD:0000000
UC-RECUT-AFTER-A-RULING:0000000
UC-RENAME-A-TERM:0000000
UC-TOGGLE-A-SYSTEM:0000000
UC-WRITE-A-VIEW-BY-HAND:0000000
<<<
RELATIONS:
- TYPE: Parent
  VALUE: UC-RENAME-A-TERM
  ROLE: Cites
- TYPE: Parent
  VALUE: UC-RECUT-AFTER-A-RULING
  ROLE: Cites
- TYPE: Parent
  VALUE: UC-FLIP-THE-VIEW
  ROLE: Cites
- TYPE: Parent
  VALUE: UC-FOLLOW-A-LINE-HOME
  ROLE: Cites
- TYPE: Parent
  VALUE: UC-READ-THE-CANON-APART-FROM-THE-WHITEBOARD
  ROLE: Cites
- TYPE: Parent
  VALUE: UC-TOGGLE-A-SYSTEM
  ROLE: Cites
- TYPE: Parent
  VALUE: UC-WRITE-A-VIEW-BY-HAND
  ROLE: Cites
