[DOCUMENT]
TITLE: The wireline: one versioned JSON payload for the whole canon, computed from the export by a backed script

[GRAMMAR]
IMPORT_FROM_FILE: @repo

[MECHANISM]
UID: MECH-VIEW-WIRELINE
TITLE: The wireline: one versioned JSON payload for the whole canon, computed from the export by a backed script
AUTHORED_BY: llm
STATEMENT: >>>
wireline.py reads the strictdoc JSON export and the worktree (to map a UID to
its file), asks the resident scribe daemon for workspace.grammar and validates
the scribe-grammar/1 reply, then writes one payload for the whole canon, schema
whiteboard-view/2, that the renderer and nothing else consumes; --root UID
narrows it to one root. Without a daemon it exits non-zero with the shared
NoDaemon socket and start remedy; it never opens grammar.sgra or imports the
grammar parser.

What is in it. The trees: every root narrative, or the one asked for, with each
root's tree fully expanded in Contains order; every narrative carries its
fields verbatim and its STATEMENT parsed per WIDGET into paragraphs, rows
(text spans, link spans, the trailing bracket word and its "by"), glossary
terms, legend entries or table rows. The nodes: every node the trees cite or
link, with every field verbatim in grammar order, its relations in and out, its
files and its fingerprint entries. The backlinks: for each node, which rows
and which Cites point at it -- the table behind "lines on the sheet by type",
data purely in sdoc and tallied here. The pairs: live (source type, role, target
type) counts among the cited nodes, the edges diagram's data. For each Cites:
unsigned, signed or drifted (the contract hash recomputed with the fingerprint
module, imported not copied) and whether the target is superseded. The grammar:
each type's fields, kinds and option lists, taken from the daemon's
workspace.grammar reply because the export types every field as String. Ladders: each choice field's option
list with a rank so a reader can order and colour badges without the grammar.
And the checks: view-check findings, count first.

Field values pass through verbatim; everything computed sits under a key that
says so. The cache key is the newest .sdoc mtime, the grammar the daemon
served, the root UID, the schema string and the script itself.
<<<
RATIONALE: >>>
A TUI reads the same payload as the page; the payload is the contract that keeps the viewer's form open (DEC-VIEWER-FORM-UNDECIDED) while the view exists.
<<<
RELATIONS:
- TYPE: Parent
  VALUE: DEC-VIEWS-ARE-REGENERABLE
  ROLE: Governed_By
- TYPE: Parent
  VALUE: DEC-NARRATIVE-IS-THE-VIEW-NODE
  ROLE: Governed_By
- TYPE: File
  VALUE: docs/sdoc/view/wireline.py
