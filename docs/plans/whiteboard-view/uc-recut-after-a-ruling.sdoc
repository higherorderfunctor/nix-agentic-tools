[DOCUMENT]
TITLE: A ruling lands, the whiteboard is re-cut, and only the lines whose nodes changed need re-reading

[GRAMMAR]
IMPORT_FROM_FILE: @repo

[USE_CASE]
UID: UC-RECUT-AFTER-A-RULING
TITLE: A ruling lands, the whiteboard is re-cut, and only the lines whose nodes changed need re-reading
AUTHORED_BY: llm
STATEMENT: >>>
A decision is accepted. The section narratives that Cites it show a drifted
citation; the operator reads those sections, re-cuts their rows, and re-signs.
Sections that cite nothing that changed stay signed and are not re-read.
The page is regenerated by the task with no renderer change and no
re-authoring of unchanged lines.
<<<
RELATIONS:
- TYPE: Parent
  VALUE: DEC-NARRATIVE-IS-THE-VIEW-NODE
  ROLE: Covered_By
- TYPE: Parent
  VALUE: MECH-VIEW-TASK
  ROLE: Covered_By
