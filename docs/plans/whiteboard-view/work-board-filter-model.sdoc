[DOCUMENT]
TITLE: Decide the Board's filter model from what the explorer finds

[GRAMMAR]
IMPORT_FROM_FILE: @repo

[WORK]
UID: WORK-BOARD-FILTER-MODEL
TITLE: Decide the Board's filter model from what the explorer finds
AUTHORED_BY: llm
STATEMENT: >>>
The whole-canon Board is denser than a person can read -- the operator's words
on 2026-09-01: too much data to be useful today; I need to get my arms around
the data to decide the best way to filter. Use the Perspective view to find
which cuts of the data earn a place on the canvas (by system, by type, by
neighbourhood, by state -- to be discovered, not presumed), then decide the
Board's filter model and supersede the no-filter clause of
REQ-SDOC-BOARD-MVP-READS-WHOLE-CANON with it. The explorer exists to answer
this question.
<<<
RELATIONS:
- TYPE: Parent
  VALUE: MECH-SDOC-BOARD-CANVAS
  ROLE: Crosses
- TYPE: Parent
  VALUE: MECH-BACKLOG-WHITEBOARD-VIEW
  ROLE: Backlogged_In
