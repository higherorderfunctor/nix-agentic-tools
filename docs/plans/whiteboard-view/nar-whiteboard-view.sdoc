[DOCUMENT]
TITLE: Whiteboard view

[GRAMMAR]
IMPORT_FROM_FILE: @repo

[NARRATIVE]
UID: NAR-WHITEBOARD-VIEW
TITLE: Whiteboard view
AUTHORED_BY: llm
WIDGET: prose
STATEMENT: >>>
How the canon is rendered for a person, and how to keep the render honest.
This is the root of the view system's own design, rendered by the same
programs that render the semantic-layer whiteboard, so what a screen here
shows is what those programs do. Nothing here is more settled than its node
says: an accepted decision is in force, an open one is a question, a
mechanism may be designed and not yet built, and a use
case is a path that must work.

The strip beneath says how settled each screen's rows are, and the stack
says what the pipeline does from the export to the page. The data model
lists the rulings the view rests on, the programs list the code that
carries them out, the rules say who enforces each, and the paths are the
use cases; the questions still open have a screen of their own. What a
rendered page is, is ruled by [LINK: DEC-VIEWS-ARE-REGENERABLE]: a
regenerable deliverable, never the source.
<<<
PARENT_FP: >>>
DEC-VIEWS-ARE-REGENERABLE:0000000
<<<
RELATIONS:
- TYPE: Parent
  VALUE: DEC-VIEWS-ARE-REGENERABLE
  ROLE: Cites
- TYPE: Child
  VALUE: NAR-WHITEBOARD-VIEW-LEGEND
  ROLE: Contains
- TYPE: Child
  VALUE: NAR-WHITEBOARD-VIEW-START-COUNTS
  ROLE: Contains
- TYPE: Child
  VALUE: NAR-WHITEBOARD-VIEW-PIPELINE
  ROLE: Contains
- TYPE: Child
  VALUE: NAR-WHITEBOARD-VIEW-DATA-MODEL
  ROLE: Contains
- TYPE: Child
  VALUE: NAR-WHITEBOARD-VIEW-PROGRAMS
  ROLE: Contains
- TYPE: Child
  VALUE: NAR-WHITEBOARD-VIEW-RULES
  ROLE: Contains
- TYPE: Child
  VALUE: NAR-WHITEBOARD-VIEW-PATHS
  ROLE: Contains
- TYPE: Child
  VALUE: NAR-WHITEBOARD-VIEW-OPEN
  ROLE: Contains
- TYPE: Child
  VALUE: NAR-WHITEBOARD-VIEW-EDGES
  ROLE: Contains
