[DOCUMENT]
TITLE: The rules, and who enforces each

[GRAMMAR]
IMPORT_FROM_FILE: @repo

[NARRATIVE]
UID: NAR-WHITEBOARD-VIEW-RULES
TITLE: The rules, and who enforces each
AUTHORED_BY: llm
WIDGET: rows
PLACE: screen
STATEMENT: >>>
The porting inventory: every rule a rendered view relies on, with who enforces it today. Some the parser refuses at export, some a script catches and is listed here for it, and two have no enforcer yet. A rule in a script is allowed for now on the operator's ruling that validation need not be modelled on joints yet, provided each such rule is indexed on this screen.

- A Cites that names a node not in the export refuses the export. [STRICTDOC]
- An inline link token in a STATEMENT whose UID does not exist refuses the export. [STRICTDOC]
- A relation role the source type does not register refuses the export. [STRICTDOC]
- A field out of grammar order, or a WIDGET or PLACE word off the list, refuses the export. [STRICTDOC]
- contains-is-a-tree: a narrative is contained at most once, by one container over the whole canon, and Contains never closes a cycle.
[LINK: MECH-VIEW-CHECK] [SCRIPT]
- contains-target-is-narrative: a Contains target is a NARRATIVE.
[LINK: MECH-VIEW-CHECK] [SCRIPT]
- place-of-root: a root carries no PLACE; it is the page.
[LINK: MECH-VIEW-CHECK] [SCRIPT]
- over-target-is-a-narrative: an Over target is a NARRATIVE.
[LINK: MECH-VIEW-CHECK] [SCRIPT]
- over-in-plan-or-spec: an Over target sits in the same plan as the widget narrative, or in the spec.
[LINK: MECH-VIEW-CHECK] [SCRIPT]
- over-unfingerprinted: no PARENT_FP entry names an Over target that is not also cited; Over says where to look, never what is true.
[LINK: MECH-VIEW-CHECK] [SCRIPT]
- legend-word: every row bracket word is in the root's legend, the narrative with the legend widget anywhere in its tree; bracket words with no legend at all is one finding at the root.
[LINK: MECH-VIEW-CHECK] [SCRIPT]
- legend-parts: a legend row is 'WORD: colour: meaning' or 'WORD: colour: meaning: by-label'.
[LINK: MECH-VIEW-CHECK] [SCRIPT]
- widget-shape: a STATEMENT has the shape its WIDGET says: a row widget has at least one row unless its data is elsewhere, glossary rows split on the first colon, a legend colour is in the vocabulary, a table has a header row with pipes and a data row.
[LINK: MECH-VIEW-CHECK] [SCRIPT]
- grid-shape: grid rows are axis captions, cells or the outside strip; every cell axis word has a caption and every caption is used.
[LINK: MECH-VIEW-CHECK] [SCRIPT]
- stack-shape: a stack row is '- NAME: label: description'.
[LINK: MECH-VIEW-CHECK] [SCRIPT]
- ladder-field-exists: a ladder row's FIELD is a field some grammar element declares.
[LINK: MECH-VIEW-CHECK] [SCRIPT]
- facts-shape: a facts row is '- label: value'.
[LINK: MECH-VIEW-CHECK] [SCRIPT]
- query-word-known: a TAGS word that is a query word in the wrong case, or two query words on one narrative, is a finding; the list is closed.
[LINK: MECH-VIEW-CHECK] [LINK: MECH-VIEW-QUERIES] [SCRIPT]
- systems-table: exactly one narrative is tagged systems, its WIDGET is table, and its header holds system, types, roles and meaning.
[LINK: MECH-VIEW-CHECK] [SCRIPT]
- cited-node-superseded: a cited node is not superseded.
[LINK: MECH-VIEW-CHECK] [SCRIPT]
- nothing-depends-on-a-narrative: no node outside the representation family points a Parent relation or a fingerprint entry at a narrative.
[LINK: MECH-VIEW-CHECK] [SCRIPT]
- title-holds-a-link: a TITLE holds no inline link token, which is inert there.
[LINK: MECH-VIEW-CHECK] [SCRIPT]
- reference-line-links-resolve: a link on a row's reference line names a node in the export; on a real export the parser refuses it first, and the rule stands for payloads built by hand.
[LINK: MECH-VIEW-CHECK] [SCRIPT]
- orphan-narrative: under a single-root render, another root outside the tree is a note, never a finding.
[LINK: MECH-VIEW-CHECK] [SCRIPT]
- A recorded fingerprint that no longer matches its parent's current contract is reported as drifted, and a placeholder as never signed.
[LINK: MECH-FP-CHECK] [SCRIPT]
- Role-carrying relations close no cycle, which the parser's own cycle check never sees.
[LINK: MECH-CYCLE-CHECK] [SCRIPT]
- A relation's target has the type its role expects, across the whole export and not only inside a view's tree.
[LINK: MECH-RELATION-TARGET-TYPE-LINT] [UNBUILT]
- No Parent relation crosses from one plan directory into another, and Cites is one.
[LINK: MECH-PLAN-REFS-CHECK] [UNBUILT]
<<<
PARENT_FP: >>>
MECH-VIEW-CHECK:0000000
MECH-VIEW-QUERIES:0000000
NAR-TERM-JOINT:0000000
<<<
RELATIONS:
- TYPE: Parent
  VALUE: MECH-VIEW-CHECK
  ROLE: Cites
- TYPE: Parent
  VALUE: NAR-TERM-JOINT
  ROLE: Cites
- TYPE: Parent
  VALUE: MECH-VIEW-QUERIES
  ROLE: Cites
